FME workspace FunksjonellVegklasse.fmw

Parameters:
- START = 2   # Første fylkesnummer
- NUM = 1   # Antall fylker
- dataFolder = O:\1\Res\16080 Geodata\Fagområde Vegnett\Vegnett spesialistfunksjon\Feil og kvalitetskontroller i NVDB\FME-kontroller\Funksjonell vegklasse\Data   # Mappe for resultatfiler
- today:   # Python Script
      import time
      ## dd/mm/yyyy format
      time.strftime("%Y%m%d")

Writers:
- XLSXW_1: XLSXW to $(dataFolder)\$(today)\FunksjonellVegklasse.xls
- SPATIALITE_1: SPATIALITE to $(dataFolder)\$(today)\FunksjonellVegklasse.db
- TEXTLINE_1: TEXTLINE to $(dataFolder)\$(today)

Note: Finne tilknyttet hovedveg med samme vegident
NeighborFinder
    INSERT_VERTEX = No
    INCOMING_PREFIX = HV_
    MAX = 1
    ATTR_ACCUM_MODE = Prefix Candidate
    K = 1
    CANDIDATES_FIRST = No
    TREAT_POLYGON_AS = Lines
    GROUP_BY = Vegreferanse.vegkategori Vegreferanse.vegstatus Vegreferanse.vegnummer
    MODE = Bases and Candidates
    MATCHED -> AttributeKeeper_7
    UNMATCHED_BASE -> Ikke_kobla_til_hovedveg
AttributeKeeper_7
    KEEP_ATTRS = NVDB_ID,Vegreferanse.vegnummer,vegklasse,Vegreferanse.kommune,HV_vegklasse,merknad,Vegreferanse.hovedparsell,Vegreferanse.vegkategori,Vegreferanse.fylke,Vegreferanse.vegstatus
    -> BoundsExtractor_3
    -> TestFilter_2
    -> NeighborFinder_2 [CANDIDATE]
    -> Ramper_og_hovedveg
Note: Rampe_Hovedveg
AttributeManager_3_OUTPUT_Output_-__text_line_5: Junction
    -> AttributeManager_3_OUTPUT_Output_-__text_line_3
Note: Finne tilknyttet rampe og hovedvegen sin vegklasse
NeighborFinder_2
    INSERT_VERTEX = No
    MAX = 1
    ATTR_ACCUM_MODE = Merge Candidate
    ATTR_CONFLICT_RES = Use Base
    K = 1
    CANDIDATES_FIRST = No
    TREAT_POLYGON_AS = Lines
    MODE = Bases and Candidates
    MATCHED -> AttributeKeeper_3
    MATCHED -> SpatialRelator [Supplier]
    UNMATCHED_BASE -> Rundkjøring_ikke_tilknytta_rampe
AttributeKeeper_3
    KEEP_ATTRS = NVDB_ID,Vegreferanse.vegnummer,vegklasse,Vegreferanse.kommune,HV_vegklasse,merknad,Vegreferanse.hovedparsell,Vegreferanse.vegkategori,Vegreferanse.fylke,Vegreferanse.vegstatus
    -> TestFilter_4
    -> Rundkjøring_med_hovedveg
Rundkjøring_med_hovedveg: Inspector
Note: Ramperundkjøring_Hovedveg
AttributeManager_3_OUTPUT_Output_-__text_line_6: Junction
    -> AttributeManager_3_OUTPUT_Output_-__text_line_3
Rundkjøring_ikke_tilknytta_rampe: Inspector
Ikke_kobla_til_hovedveg: Inspector
    TACKATTRS = Vegreferanse.vegkategori
AttributeKeeper_8
    KEEP_ATTRS = Vegreferanse.kommune,vegklasse,Vegreferanse.hovedparsell,Vegreferanse.vegkategori,Vegreferanse.vegstatus,Vegreferanse.fylke,Vegreferanse.vegnummer
    -> NeighborFinder_4 [CANDIDATE]
Note: Kryssende_veg
AttributeManager_3_OUTPUT_Output_-__text_line_7: Junction
    -> AttributeManager_3_OUTPUT_Output_-__text_line_3
FlerePrRundkjøring: Inspector
    TACKATTRS = _antall
AttributeManager_2
    ATTR_TABLE:
      RENAME_SET_VALUE Vegreferanse.fylke > fylke
      RENAME_SET_VALUE Vegreferanse.kommune > kommune
      RENAME_SET_VALUE Vegreferanse.vegkategori > vegkategori
      RENAME_SET_VALUE Vegreferanse.vegstatus > vegstatus
      RENAME_SET_VALUE Vegreferanse.vegnummer > vegnummer
      RENAME_SET_VALUE Vegreferanse.hovedparsell > hovedparsell
      SET_TO _feil = Rundkjøring har flere vegklasser
    -> Flere_klasser_rundkjøring (writer XLSXW_1)
    -> flere_klasser_rundkjoring (writer SPATIALITE_1)
    -> AttributeManager_2_OUTPUT
Flere_klasser_rundkjøring (writer XLSXW_1)
    attributes: fylke number(20), kommune number(20), vegkategori auto(20), vegstatus auto(20), vegnummer number(20), hovedparsell number(20), vegklasse string(20)
flere_klasser_rundkjoring (writer SPATIALITE_1)
    attributes: fylke integer, kommune integer, vegkategori string(2), vegstatus string(2), vegnummer integer, hovedparsell integer, vegklasse string(20)
Note: GL Feilfil
AttributeManager_2_OUTPUT: Junction
    -> AttributeManager_3_OUTPUT_Output_-__text_line_4
Note: Flere_klasser_rundkjøring
AttributeManager_3_OUTPUT_Output_-__text_line_4: Junction
    -> AttributeManager_3_OUTPUT_Output_-__text_line_3
Note: Lenker tilknyttet rundkjøringene
SpatialRelator_2
    SUCCESS_ATTR = _related_candidates
    CURVE_BOUNDARY_RULE_PARAM = Default Rule
    CALC_CARD = No
    AGGREGATE_HANDLING = Yes
    PREDICATES = INTERSECTS
    LIST_NAME = _relationships
    -> ListSorter
Note: Sorterer tilknytta lenker på vegklasse
ListSorter
    SRC_LIST = _relationships{}.vegklasse
    ORDER = Ascending
    TYPE = Numeric
    -> ListIndexer
ListIndexer
    LIST_ATTR = _relationships{}
    PREFIX = HV_
    INDEX = 0
    -> TestFilter_11
Note: Finner de som har annen vegklasse en laveste verdi på tilstøtende lenke (høyeste klasse)
TestFilter_11
    TEST_LIST = BOOL_OP,OR,COMPOSITE_TEST,<Unused>,TEST_CLAUSE,"TEST @Value(vegklasse) != @Value(HV_vegklasse)",Annen vegklasse
    DEFAULT_VALUE = <UNFILTERED>
    Annen vegklasse -> AttributeRemover
AttributeRemover
    LIST_ATTRS = HV__headers{} HV__hierarchy_child_id_list{} HV_assosiasjoner{} HV_lineærPosisjon{} HV_pass{} _headers{} _hierarchy_child_id_list{} _relationships{} assosiasjoner{} lineærPosisjon{}
    -> AttributeManager_4
AttributeManager_4
    ATTR_TABLE:
      RENAME_SET_VALUE Vegreferanse.fylke > fylke
      RENAME_SET_VALUE Vegreferanse.kommune > kommune
      RENAME_SET_VALUE Vegreferanse.vegkategori > vegkategori
      RENAME_SET_VALUE Vegreferanse.vegstatus > vegstatus
      RENAME_SET_VALUE Vegreferanse.vegnummer > vegnummer
      RENAME_SET_VALUE Vegreferanse.hovedparsell > hovedparsell
      SET_TO nvdb_id = @Value(NVDB_ID)
      SET_TO hv_vegklasse = @Value(HV_vegklasse)
      SET_TO _feil = Rundkjøring har annen vegklasse enn høyeste klasse på tilstøtende veg
    -> GeometryReplacer
GeometryReplacer
    SOURCE = @Value(_geometry)
    REMOVE_ATTRIBUTE = Yes
    KIND_LONG = FME Binary
    -> RundkjøringTilstøtendeveg (writer XLSXW_1)
    -> rundkjoring_tilstotendeveg (writer SPATIALITE_1)
    -> Annen_vegklasse_enn_laveste
    -> AttributeManager_4_OUTPUT
Annen_vegklasse_enn_laveste: Inspector
RundkjøringTilstøtendeveg (writer XLSXW_1)
    attributes: NVDB_ID number(20), fylke number(20), kommune number(20), vegkategori auto(20), vegstatus auto(20), vegnummer number(20), hovedparsell number(20), vegklasse number(20), HV_vegklasse number(20), merknad string(20)
rundkjoring_tilstotendeveg (writer SPATIALITE_1)
    attributes: nvdb_id integer64, fylke integer, kommune integer, vegkategori string(2), vegstatus string(2), vegnummer integer, hovedparsell integer, vegklasse integer, hv_vegklasse integer
Note: GL Feilfil
AttributeManager_4_OUTPUT: Junction
    -> AttributeManager_3_OUTPUT_Output_-__text_line_2
Note: Rundkjøring_tilstøtendeveg
AttributeManager_3_OUTPUT_Output_-__text_line_2: Junction
    -> AttributeManager_3_OUTPUT_Output_-__text_line_3
AttributeManager_3_OUTPUT_Output_-__text_line_3: Junction
    -> NeighborFinder_5 [CANDIDATE]
    -> CenterPointReplacer
Sorter
    SORT_PARM = kortform ALPHA ASCENDING
    SORTED -> StringConcatenator_2
StringConcatenator_2
    ACTION = Create New Attribute
    PARM_LINE = FEIL: @Value(_y) @Value(_x) @Value(_feil), vegreferanse @Value(kortform)
    VAL_ATTR = text_line_data
    -> text_line (writer TEXTLINE_1)
Note: Fylkesvise GL Feilfiler
text_line (writer TEXTLINE_1)
    attributes: text_line_data buffer
FVK_VedRundkjøring: Inspector [off]

Bookmark: Utvalg (antall fylker og nummer)
Creator_2
    GEOMTYPE = Geometry Object
    NUM = $(NUM)
    CREATED -> Counter_2
Counter_2
    DOMAIN = counter
    CNT_ATTR = _count
    START = $(START)
    SCOPE = Global
    -> AttributeCreator_8
    -> AttributeCreator_11

Bookmark: Leser Vegreferanseobjekter på rampe fra NVDB API for å finne rampesystemer
AttributeCreator_11
    ATTR_TABLE = SET_TO href = https://www.vegvesen.no/nvdb/api/v2/vegobjekter/532?fylke=@Value(_count)&egenskap="4569>=70 AND 4569<=199 AND 4567=5499"&antall=5000&inkluder=alle
    -> LesVegreferanseobjekter
LesVegreferanseobjekter
    HREF = @Value(href)
    -> AttributeCreator_3
    -> Rampesystem
Rampesystem: Inspector

Bookmark: Leser Funksjonell Vegklasse innenfor avgrensningen fra NVDB
AttributeCreator_3
    ATTR_LIST = href,https://www.vegvesen.no/nvdb/api/v2/vegobjekter/821?kartutsnitt=@Value(_xmin),@Value(_ymin),@Value(_xmax),@Value(_ymax)&vegreferanse=@Value(_vk)V@Value(vegnummer)&antall=5000&inkluder=alle
    NUM_SUBSEQUENT_FEATURES = 0
    NUM_PRIOR_FEATURES = 0
    -> AttributeKeeper_2
AttributeKeeper_2
    KEEP_ATTRS = href
    -> LesFunksjonellVegklasseobjekter
LesFunksjonellVegklasseobjekter
    HREF = @Value(href)
    -> TestFilter
TestFilter
    TEST_LIST = BOOL_OP,OR,COMPOSITE_TEST,<Unused>,TEST_CLAUSE,"TEST @Value(Vegreferanse.hovedparsell) IN 70-199",Ramper,BOOL_OP,OR,COMPOSITE_TEST,<Unused>,TEST_CLAUSE,"TEST @Value(Vegreferanse.hovedparsell) <= 49",Hovedveg
    DEFAULT_VALUE = <UNFILTERED>
    Ramper -> Ramper
    Ramper -> NeighborFinder [BASE]
    Hovedveg -> Hovedveg
    Hovedveg -> NeighborFinder [CANDIDATE]
    Hovedveg -> AttributeKeeper_8
Ramper: Inspector
Hovedveg: Inspector

Bookmark: Ulik vegklasse rampe og hovedveg
TestFilter_2
    TEST_LIST = BOOL_OP,OR,COMPOSITE_TEST,<Unused>,TEST_CLAUSE,"TEST @Value(vegklasse) != @Value(HV_vegklasse)",Ulik vegklasse
    DEFAULT_VALUE = <UNFILTERED>
    Ulik vegklasse -> Ulik_vegklasse_rampe
    Ulik vegklasse -> Matcher_3
Ulik_vegklasse_rampe: Inspector
Matcher_3
    MATCH_STRATEGY = Match All Attributes
    CNT_ATTR = _match_id
    BLANK_AND_MISSING_DIFFER = No
    MATCH = NONE
    LENIENT_MATCH = No
    SINGLE_MATCHED -> AttributeManager_3
    NOT_MATCHED -> AttributeManager_3
AttributeManager_3
    ATTR_TABLE:
      RENAME_SET_VALUE Vegreferanse.fylke > fylke
      RENAME_SET_VALUE Vegreferanse.kommune > kommune
      RENAME_SET_VALUE Vegreferanse.vegkategori > vegkategori
      RENAME_SET_VALUE Vegreferanse.vegstatus > vegstatus
      RENAME_SET_VALUE Vegreferanse.vegnummer > vegnummer
      REMOVE _match_id
      RENAME_SET_VALUE Vegreferanse.hovedparsell > hovedparsell
      SET_TO nvdb_id = @Value(NVDB_ID)
      SET_TO hv_vegklasse = @Value(HV_vegklasse)
      SET_TO _feil = Rampe har annen vegklasse enn tilhørende hovedveg
    -> Rampe_Hovedveg (writer XLSXW_1)
    -> rampe_hovedveg (writer SPATIALITE_1)
    -> AttributeManager_3_OUTPUT
Note: text_line_2 : Input
AttributeManager_3_OUTPUT: Junction
    -> AttributeManager_3_OUTPUT_Output
Note: GL Feilfil
AttributeManager_3_OUTPUT_Output: Junction
    -> AttributeManager_3_OUTPUT_Output_-__text_line_5
Rampe_Hovedveg (writer XLSXW_1)
    attributes: NVDB_ID number(20), fylke number(20), kommune number(20), vegkategori auto(20), vegstatus auto(20), vegnummer number(20), hovedparsell number(20), vegklasse number(20), HV_vegklasse number(20), merknad string(20)
rampe_hovedveg (writer SPATIALITE_1)
    attributes: nvdb_id integer64, fylke integer, kommune integer, vegkategori string(2), vegstatus string(2), vegnummer integer, hovedparsell integer, vegklasse integer, hv_vegklasse integer
Ramper_og_hovedveg: Inspector

Bookmark: Leser Vegreferanseobjekter på rundkjøring innenfor rampene sin bounding box
BoundsExtractor_3
    XMAX = _xmax
    ZMAX = _zmax
    ZMIN = _zmin
    YMAX = _ymax
    XMIN = _xmin
    YMIN = _ymin
    -> AttributeCreator_5
AttributeCreator_5
    ATTR_LIST = href,https://www.vegvesen.no/nvdb/api/v2/vegobjekter/532?kartutsnitt=@Value(_xmin),@Value(_ymin),@Value(_xmax),@Value(_ymax)&egenskap="4569>=400 AND 4569<=599  AND 4567=5499"&antall=5000&inkluder=alle
    NUM_SUBSEQUENT_FEATURES = 0
    NUM_PRIOR_FEATURES = 0
    -> LesVegreferanseobjekter_2
LesVegreferanseobjekter_2
    HREF = @Value(href)
    -> Rundkjøringer_ved_ramper
    -> AttributeCreator_4
    -> AttributeCreator_6
Rundkjøringer_ved_ramper: Inspector

Bookmark: Leser Funksjonell Vegklasse på lenker i rundkjøringene
AttributeCreator_4
    ATTR_LIST = href,https://www.vegvesen.no/nvdb/api/v2/vegobjekter/821?kartutsnitt=@Value(_xmin),@Value(_ymin),@Value(_xmax),@Value(_ymax)&vegreferanse=@Value(_vk)V@Value(vegnummer)HP@Value(hovedparsell)&antall=5000&inkluder=alle
    NUM_SUBSEQUENT_FEATURES = 0
    NUM_PRIOR_FEATURES = 0
    -> AttributeKeeper_6
AttributeKeeper_6
    KEEP_ATTRS = href
    -> LesFunksjonellVegklasseobjekter_2
Note: Funksjonell vegklasse for veger innen boundingbox, med vegident + hp for rundkjøringene
LesFunksjonellVegklasseobjekter_2
    HREF = @Value(href)
    -> TestFilter_3
Note: Finner rundkjøringer
TestFilter_3
    TEST_LIST:
      BOOL_OP,OR,COMPOSITE_TEST,<Unused>,TEST_CLAUSE,"TEST @Value(Vegreferanse.hovedparsell) IN 400-599",Rundkjøring,BOOL_OP,OR,COMPOSITE_TEST,<Unused>,TEST_CLAUSE,"TEST @Value(Vegreferanse.hovedparsell) IN 1-49
      TEST @Value(Vegreferanse.hovedparsell) IN 50-69
      TEST @Value(Vegreferanse.hovedparsell) IN 600-699",Andre
    DEFAULT_VALUE = Ramper
    Rundkjøring -> NeighborFinder_2 [BASE]

Bookmark: Ulik vegklasse rundkjøring og hovedveg
TestFilter_4
    TEST_LIST = BOOL_OP,OR,COMPOSITE_TEST,<Unused>,TEST_CLAUSE,"TEST @Value(vegklasse) != @Value(HV_vegklasse)",Ulik vegklasse
    DEFAULT_VALUE = <UNFILTERED>
    Ulik vegklasse -> Ulik_vegklasse_Rundkjøring
    Ulik vegklasse -> Matcher_6
Ulik_vegklasse_Rundkjøring: Inspector
Matcher_6
    MATCH_STRATEGY = Match All Attributes
    CNT_ATTR = _match_id
    BLANK_AND_MISSING_DIFFER = No
    MATCH = NONE
    LENIENT_MATCH = No
    SINGLE_MATCHED -> AttributeManager_6
    NOT_MATCHED -> AttributeManager_6
AttributeManager_6
    ATTR_TABLE:
      RENAME_SET_VALUE Vegreferanse.fylke > fylke
      RENAME_SET_VALUE Vegreferanse.kommune > kommune
      RENAME_SET_VALUE Vegreferanse.vegkategori > vegkategori
      RENAME_SET_VALUE Vegreferanse.vegstatus > vegstatus
      RENAME_SET_VALUE Vegreferanse.vegnummer > vegnummer
      REMOVE _match_id
      RENAME_SET_VALUE Vegreferanse.hovedparsell > hovedparsell
      SET_TO nvdb_id = @Value(NVDB_ID)
      SET_TO hv_vegklasse = @Value(HV_vegklasse)
      SET_TO _feil = Rundkjøring tilknyttet rampe har annen vegklasse enn tilhørende hovedveg
    -> Ramperundkjøring_Hovedveg (writer XLSXW_1)
    -> ramperundkjoring_hovedveg (writer SPATIALITE_1)
    -> AttributeManager_6_OUTPUT
Ramperundkjøring_Hovedveg (writer XLSXW_1)
    attributes: NVDB_ID number(20), fylke number(20), kommune number(20), vegkategori auto(20), vegstatus auto(20), vegnummer number(20), hovedparsell number(20), vegklasse number(20), HV_vegklasse number(20), merknad string(20)
ramperundkjoring_hovedveg (writer SPATIALITE_1)
    attributes: nvdb_id integer64, fylke integer, kommune integer, vegkategori string(2), vegstatus string(2), vegnummer integer, hovedparsell integer, vegklasse integer, hv_vegklasse integer
Note: GL Feilfil
AttributeManager_6_OUTPUT: Junction
    -> AttributeManager_3_OUTPUT_Output_-__text_line_6

Bookmark: Leser Funksjonell Vegklasse på ALLE veger ved rundkjøringene
AttributeCreator_6
    ATTR_LIST = href,https://www.vegvesen.no/nvdb/api/v2/vegobjekter/821?kartutsnitt=@Value(_xmin),@Value(_ymin),@Value(_xmax),@Value(_ymax)&antall=5000&inkluder=alle
    NUM_SUBSEQUENT_FEATURES = 0
    NUM_PRIOR_FEATURES = 0
    -> AttributeKeeper_10
AttributeKeeper_10
    KEEP_ATTRS = href
    -> LesFunksjonellVegklasseobjekter_3
LesFunksjonellVegklasseobjekter_3
    HREF = @Value(href)
    -> TestFilter_6
Note: Utelater rundkjøringer og ramper
TestFilter_6
    TEST_LIST:
      BOOL_OP,OR,COMPOSITE_TEST,<Unused>,TEST_CLAUSE,"TEST @Value(Vegreferanse.hovedparsell) IN 1-49
      TEST @Value(Vegreferanse.hovedparsell) IN 50-69
      TEST @Value(Vegreferanse.hovedparsell) IN 600-699",Andre,BOOL_OP,OR,COMPOSITE_TEST,<Unused>,TEST_CLAUSE,"TEST @Value(Vegreferanse.hovedparsell) IN 400-599",Rundkjøring
    DEFAULT_VALUE = Ramper
    Andre -> SpatialRelator [Requestor]

Bookmark: Finner lenker som krysser hovedveg, der det ligger minst to ramperundkjøringer innenfor 500m fra krysningspunktet
Note: Finner sammenheng mellom lenker rundt ramperundkjøringer og rundkjøringene / Requestor: Andre veger ved rundkjøringer / Supplier: Rundkjøring ved rampe
SpatialRelator
    SUCCESS_ATTR = _related_candidates
    CURVE_BOUNDARY_RULE_PARAM = Default Rule
    CALC_CARD = No
    AGGREGATE_HANDLING = Yes
    PREDICATES = INTERSECTS
    LIST_NAME = _relationships
    -> TestFilter_7
Note: Lenker som berører minst to rundkjøringer
TestFilter_7
    TEST_LIST = BOOL_OP,OR,COMPOSITE_TEST,<Unused>,TEST_CLAUSE,"TEST @Value(_related_candidates) >= 2",MinstTo
    DEFAULT_VALUE = <UNFILTERED>
    MinstTo -> NeighborFinder_4 [BASE]
Note: Lenker som krysser hovedveg ved ramper
NeighborFinder_4
    INSERT_VERTEX = No
    INCOMING_PREFIX = _cc
    MAX = 1
    ATTR_ACCUM_MODE = Prefix Candidate
    K = 1
    CANDIDATES_FIRST = No
    TREAT_POLYGON_AS = Lines
    MODE = Bases and Candidates
    MATCHED -> TestFilter_12
Note: Fjerner tilfeller av at samme parsell er både kryssende veg og hovedveg (ramper fra kryssende veg)
TestFilter_12
    TEST_LIST:
      BOOL_OP,AND,COMPOSITE_TEST,<Unused>,TEST_CLAUSE,"TEST @Value(_ccVegreferanse.vegkategori) = @Value(Vegreferanse.vegkategori)
      TEST @Value(_ccVegreferanse.vegnummer) = @Value(Vegreferanse.vegnummer)
      TEST @Value(_ccVegreferanse.hovedparsell) = @Value(Vegreferanse.hovedparsell)",SammeParsell
    DEFAULT_VALUE = <UNFILTERED>
    <UNFILTERED> -> Counter_3
Counter_3
    DOMAIN = counter
    CNT_ATTR = _caseNumber
    START = 0
    SCOPE = Global
    -> VertexCreator
    -> AttributeKeeper_9
AttributeKeeper_9
    KEEP_ATTRS = NVDB_ID,Vegreferanse.vegnummer,vegklasse,Vegreferanse.kommune,_caseNumber,HV_vegklasse,_closest_base_y,merknad,_closest_base_x,Vegreferanse.hovedparsell,Vegreferanse.vegkategori,Vegreferanse.fylke,_related_candidates,Vegreferanse.vegstatus
    -> Kryssende_veg_ved_rundkjøring
    -> FeatureMerger [REQUESTOR]
Kryssende_veg_ved_rundkjøring: Inspector [off]
Note: Lager krysningpunktet
VertexCreator
    XVAL = @Value(_closest_base_x)
    YVAL = @Value(_closest_base_y)
    MODE_NAME = Replace with Point
    -> ListExploder_4
    -> AttributeKeeper_11
AttributeKeeper_11
    KEEP_ATTRS = _caseNumber
    -> NeighborFinder_3 [BASE]
ListExploder_4
    LIST_ATTR = _relationships{}
    INDEX_ATTR = _element_index
    INCOMING_PREFIX = _related
    ATTR_ACCUM_MODE = Prefix Incoming List
    ELEMENTS -> VertexCreator_2
Note: Lager punkt for nærliggende rundkjøring
VertexCreator_2
    XVAL = @Value(_related_closest_base_x)
    YVAL = @Value(_related_closest_base_y)
    MODE_NAME = Replace with Point
    -> AttributeKeeper_12
AttributeKeeper_12
    KEEP_ATTRS = _caseNumber
    -> NeighborFinder_3 [CANDIDATE]
Note: Finner sammenhenger innenfor 500m
NeighborFinder_3
    INSERT_VERTEX = No
    MAX = 500
    CLOSE_LIST_NAME = _ccList
    ATTR_ACCUM_MODE = Merge Candidate
    ATTR_CONFLICT_RES = Use Base
    K = 2
    CANDIDATES_FIRST = No
    TREAT_POLYGON_AS = Lines
    GROUP_BY = _caseNumber
    MODE = Bases and Candidates
    MATCHED -> ListElementCounter
ListElementCounter
    CNT_ATTR = _element_count
    LIST_NAME = _ccList{}
    -> TestFilter_8
TestFilter_8
    TEST_LIST = BOOL_OP,OR,COMPOSITE_TEST,<Unused>,TEST_CLAUSE,"TEST @Value(_element_count) >= 2",MinstTo
    DEFAULT_VALUE = <UNFILTERED>
    MinstTo -> AttributeKeeper_13
AttributeKeeper_13
    KEEP_ATTRS = _caseNumber
    -> FeatureMerger [SUPPLIER]
FeatureMerger
    SUPPLIERS_FIRST = No
    MERGE_TYPE = Geometry
    PROCESS_DUPS = No
    JOIN_KEYS = @Value(_caseNumber) @Value(_caseNumber) AUTO
    MERGED -> TestFilter_5

Bookmark: Ulik vegklasse kryssende veg mellom rundkjøringer og hovedveg over eller under
TestFilter_5
    TEST_LIST = BOOL_OP,OR,COMPOSITE_TEST,<Unused>,TEST_CLAUSE,"TEST @Value(vegklasse) != @Value(HV_vegklasse)",Ulik vegklasse
    DEFAULT_VALUE = <UNFILTERED>
    Ulik vegklasse -> Matcher_7
Matcher_7
    MATCH_STRATEGY = Match All Attributes
    CNT_ATTR = _match_id
    BLANK_AND_MISSING_DIFFER = No
    MATCH = NONE
    LENIENT_MATCH = No
    SINGLE_MATCHED -> CoordinateExtractor_2
    NOT_MATCHED -> CoordinateExtractor_2
CoordinateExtractor_2
    Z_DEFAULT = 0
    IND = 0
    Z_ATTR = _z
    X_ATTR = _x
    MODE = Specify Coordinate
    Y_ATTR = _y
    -> AttributeCreator_12
AttributeCreator_12
    ATTR_TABLE = SET_TO httpReq = https://www.vegvesen.no/nvdb/api/v2/posisjon.xml?nord=@Value(_y)&ost=@Value(_x)&vegreferanse=@Value(Vegreferanse.vegkategori)@Value(Vegreferanse.vegstatus)@Value(Vegreferanse.vegnummer)
    -> HTTPCaller_3
Note: Finner vegreferanse for representasjonspunktet
HTTPCaller_3
    TARGET_URL = @Value(httpReq)
    TARGET_ATTR = _response_body
    USE_COOKIES = No
    FILE_TYPE = <Auto Detect from HTTP Headers>
    TRANSFER_TIMEOUT_LENGTH = 90
    HTTP_METHOD = GET
    VERIFY_SSL_CERTIFICATES = Yes
    CONNECTION_TIMEOUT_LENGTH = 60
    FOLLOW_REDIRECTS = Yes
    SAVE_FILE = Attribute
    ERROR_ATTR = _error
    STATUS_CODE_ATTR = _http_status_code
    TARGET_ATTR_ENCODING = auto-detect
    RESPONSE_HEADER_LIST_ATTR = _headers
    -> XMLFlattener_3
    <Rejected> -> AttributeManager_7
XMLFlattener_3
    XML_SOURCE_TYPE = Attribute with XML document
    EMBEDDED_EXPRESSIONS = vegreferanse
    ATTRIBUTE_XML = _response_body
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    NEW_ATTRIBUTES = fylke kommune kategori status nummer hp meter kortform
    -> AttributeManager_7
    -> Ulik_vegklasse_Kryssende_veg
Ulik_vegklasse_Kryssende_veg: Inspector
AttributeManager_7
    ATTR_TABLE:
      REMOVE Vegreferanse.fylke
      REMOVE Vegreferanse.kommune
      REMOVE Vegreferanse.vegkategori
      REMOVE Vegreferanse.vegstatus
      REMOVE Vegreferanse.vegnummer
      REMOVE _match_id
      REMOVE httpReq
      REMOVE _headers{}.name
      REMOVE _headers{}.value
      REMOVE _response_body
      REMOVE _http_status_code
      SET_TO nvdb_id = @Value(NVDB_ID)
      SET_TO hv_vegklasse = @Value(HV_vegklasse)
      RENAME_SET_VALUE Vegreferanse.hovedparsell > hovedparsell
      SET_TO hv_vegklasse = @Value(HV_vegklasse)
      SET_TO nvdb_id = @Value(NVDB_ID)
      SET_TO _feil = Kryssende veg mellom rundkjøringer tilknyttet rampe har annen vegklasse enn tilhørende hovedveg
      RENAME_SET_VALUE kategori > vegkategori
      RENAME_SET_VALUE status > vegstatus
      RENAME_SET_VALUE nummer > vegnummer
      RENAME_SET_VALUE hp > hovedparsell
    -> Kryssende_veg (writer XLSXW_1)
    -> kryssende_veg (writer SPATIALITE_1)
    -> AttributeManager_7_OUTPUT
kryssende_veg (writer SPATIALITE_1)
    attributes: nvdb_id integer64, fylke integer, kommune integer, vegkategori string(2), vegstatus string(2), vegnummer integer, hovedparsell integer, vegklasse integer, hv_vegklasse integer
Kryssende_veg (writer XLSXW_1)
    attributes: NVDB_ID number(20), fylke number(20), kommune number(20), vegkategori auto(20), vegstatus auto(20), vegnummer number(20), hovedparsell number(20), meter number(20), vegklasse number(20), HV_vegklasse number(20), merknad string(20)
Note: GL Feilfil
AttributeManager_7_OUTPUT: Junction
    -> AttributeManager_3_OUTPUT_Output_-__text_line_7

Bookmark: Leser Vegreferanseobjekter på rundkjøring fra NVDB API for å finne rundkjøringene
AttributeCreator_8
    ATTR_LIST = href,https://www.vegvesen.no/nvdb/api/v2/vegobjekter/532?fylke=@Value(_count)&egenskap="4569>=400 AND 4569<=599 AND 4567=5499"&antall=5000&inkluder=alle
    NUM_SUBSEQUENT_FEATURES = 0
    NUM_PRIOR_FEATURES = 0
    -> LesVegreferanseobjekter_3
LesVegreferanseobjekter_3
    HREF = @Value(href)
    -> Rundkjøringer
    -> TestFilter_13
    -> AttributeCreator_10
    -> AttributeCreator_9
Rundkjøringer: Inspector

Bookmark: Funksjonell vegklasse på rundkjøringer
TestFilter_13 [off]
    TEST_LIST:
      BOOL_OP,COMPOSITE,COMPOSITE_TEST,"""1 AND (2 OR 3)""",TEST_CLAUSE,"TEST @Value(vegnummer) = 352
      TEST @Value(hovedparsell) = 400
      TEST @Value(hovedparsell) = 401",Testobjekter
    DEFAULT_VALUE = <UNFILTERED>

Bookmark: Leser Funksjonell Vegklasse for rundkjøringene, og finner tilfeller med flere pr rundkjøring
AttributeCreator_10
    ATTR_LIST = href,https://www.vegvesen.no/nvdb/api/v2/vegobjekter/821?kartutsnitt=@Value(_xmin),@Value(_ymin),@Value(_xmax),@Value(_ymax)&vegreferanse=@Value(_vk)V@Value(vegnummer)HP@Value(hovedparsell)&antall=5000&inkluder=alle
    NUM_SUBSEQUENT_FEATURES = 0
    NUM_PRIOR_FEATURES = 0
    -> AttributeKeeper_4
AttributeKeeper_4
    KEEP_ATTRS = href
    -> LesFunksjonellVegklasseobjekter_4
LesFunksjonellVegklasseobjekter_4
    HREF = @Value(href)
    -> Aggregator_2
Aggregator_2
    AGGREGATE_TYPE = Homogeneous Collection (If Possible)
    GROUP_BY = Vegreferanse.vegnummer vegklasse Vegreferanse.kommune Vegreferanse.hovedparsell Vegreferanse.vegkategori Vegreferanse.fylke Vegreferanse.vegstatus
    MODE = Geometry - Assemble One Level
    ACCUM_ATTRS_NAME = No
    SEP = ,
    ORDERED = No
    AGGREGATE -> Aggregator
    AGGREGATE -> GeometryExtractor
Aggregator
    AGGREGATE_TYPE = Homogeneous Collection (If Possible)
    CONCAT_ATTRS = vegklasse
    GROUP_BY = Vegreferanse.vegnummer Vegreferanse.kommune Vegreferanse.hovedparsell Vegreferanse.vegkategori Vegreferanse.fylke Vegreferanse.vegstatus
    COUNT_ATTR = _antall
    MODE = Geometry - Assemble One Level
    ACCUM_ATTRS_NAME = No
    SEP = ,
    LIST_NAME = _List
    ORDERED = No
    AGGREGATE -> TestFilter_9
TestFilter_9
    TEST_LIST = BOOL_OP,OR,COMPOSITE_TEST,<Unused>,TEST_CLAUSE,"TEST @Value(_antall) >= 2",MinstTo
    DEFAULT_VALUE = <UNFILTERED>
    MinstTo -> FlerePrRundkjøring
    MinstTo -> AttributeManager_2
GeometryExtractor
    ATTR = _geometry
    OGEOSMS_URL_PREFIX = http://maps.google.com/?q=
    GEOHASH_PRECISION_DISPLAY = ~9.3 mm (12 characters)
    LEVELS_ATTR = _levels
    OMIT_NAMESPACES_DISPLAY = No
    REMOVE_GEOMETRY = No
    ELLIPSOID_NAME = WGS84
    OGC_WKT_PRECISION_DISPLAY = Shortened 64-bit
    OGCVERSION = 1.1
    LETTERING = WGS84
    KIND_LONG = FME Binary
    MSSQL_FORMAT_CHOICE = Geometry
    PREFER_POLYGON_OVER_SURFACE = No
    PRECISION = 0
    -> Bufferer
Bufferer
    CAP_STYLE = Round
    INTERP_SEGMENTS = 8
    OFFSET = 1
    BUFFERED -> SpatialRelator_2 [Requestor]

Bookmark: Leser Funksjonell Vegklasse på alle veger ved rundkjøringene
AttributeCreator_9
    ATTR_LIST = href,https://www.vegvesen.no/nvdb/api/v2/vegobjekter/821?kartutsnitt=@Value(_xmin),@Value(_ymin),@Value(_xmax),@Value(_ymax)&antall=5000&inkluder=alle
    NUM_SUBSEQUENT_FEATURES = 0
    NUM_PRIOR_FEATURES = 0
    -> AttributeKeeper_5
AttributeKeeper_5
    KEEP_ATTRS = href
    -> LesFunksjonellVegklasseobjekter_5
LesFunksjonellVegklasseobjekter_5
    HREF = @Value(href)
    -> TestFilter_10
Note: Skiller rundkjøringer og andre veger
TestFilter_10
    TEST_LIST = BOOL_OP,OR,COMPOSITE_TEST,<Unused>,TEST_CLAUSE,"TEST @Value(Vegreferanse.hovedparsell) IN 400-599",Rundkjøring
    DEFAULT_VALUE = Andre
    Andre -> SpatialRelator_2 [Supplier]
    Andre -> FVK_VedRundkjøring

Bookmark: Erstatter linjegeometri med punkt på linja
CenterPointReplacer
    CENTERPOINT -> NeighborFinder_5 [BASE]
NeighborFinder_5
    INSERT_VERTEX = No
    MAX = 10000
    CANDIDATES_FIRST = No
    TREAT_POLYGON_AS = Lines
    GROUP_BY = NVDB_ID
    MATCHED -> 2DPointReplacer
2DPointReplacer
    XVALATTR = @Value(_closest_candidate_x)
    YVALATTR = @Value(_closest_candidate_y)
    POINT -> CoordinateExtractor
CoordinateExtractor
    Z_DEFAULT = 0
    IND = 0
    Z_ATTR = _z
    X_ATTR = _x
    MODE = Specify Coordinate
    Y_ATTR = _y
    -> AttributeCreator_2
AttributeCreator_2
    ATTR_TABLE = SET_TO httpReq = https://www.vegvesen.no/nvdb/api/v2/posisjon.xml?nord=@Value(_y)&ost=@Value(_x)
    -> HTTPCaller_2
Note: Finner vegreferanse for representasjonspunktet
HTTPCaller_2
    TARGET_URL = @Value(httpReq)
    TARGET_ATTR = _response_body
    USE_COOKIES = No
    FILE_TYPE = <Auto Detect from HTTP Headers>
    TRANSFER_TIMEOUT_LENGTH = 90
    HTTP_METHOD = GET
    VERIFY_SSL_CERTIFICATES = Yes
    CONNECTION_TIMEOUT_LENGTH = 60
    FOLLOW_REDIRECTS = Yes
    SAVE_FILE = Attribute
    ERROR_ATTR = _error
    STATUS_CODE_ATTR = _http_status_code
    TARGET_ATTR_ENCODING = auto-detect
    RESPONSE_HEADER_LIST_ATTR = _headers
    -> XMLFlattener_2
XMLFlattener_2
    XML_SOURCE_TYPE = Attribute with XML document
    EMBEDDED_EXPRESSIONS = vegreferanse
    ATTRIBUTE_XML = _response_body
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    NEW_ATTRIBUTES = fylke kommune kategori status nummer hp meter kortform
    -> Sorter

FME custom transformer LesFunksjonellVegklasseobjekter
Leser funksjonell vegklasse ut fra søkekriterie

Parameters:
- HREF = @Value(href)   # href

Input (input)
    -> NVDB_Leser_3 [_Input]
NVDB_Leser_3
    NESTE.HREF = @Value(href)
    -> AttributeExposer_2
    -> FunksjonellVegklasse
FunksjonellVegklasse: Inspector [off]
AttributeExposer_2
    ATTR_LIST = 9338,10183
    -> AttributeManager
AttributeManager
    ATTR_TABLE:
      RENAME_SET_VALUE 10183 > merknad
      SET_TO NVDB_ID = @Value(identifikasjon.Identifikasjon.lokalId)
    -> AttributeValueMapper
Note: Oversetter vegklasse
AttributeValueMapper
    LUT = 13060,0,13061,1,13062,2,13063,3,13064,4,13065,5,13066,6,13067,7,13068,8,13069,9
    SRC = 9338
    VAL_ATTR = vegklasse
    DIRECTION = Forward (Source To Destination)
    -> ListExploder
Note: Pakker ut vegreferanseliste
ListExploder
    LIST_ATTR = vegreferanse{}
    INDEX_ATTR = _element_index
    ATTR_ACCUM_MODE = Merge Incoming List
    ATTR_CONFLICT_RES = Use Incoming List
    ELEMENTS -> AttributeExposer_3
AttributeExposer_3
    ATTR_LIST = Vegreferanse.fylke,Vegreferanse.kommune,Vegreferanse.vegkategori,Vegreferanse.vegstatus,Vegreferanse.vegnummer,Vegreferanse.hovedparsell
    -> Matcher_2
Note: Fjerner duplikater
Matcher_2
    MATCHATTRS = NVDB_ID Vegreferanse.vegnummer vegklasse Vegreferanse.kommune Vegreferanse.hovedparsell Vegreferanse.vegkategori Vegreferanse.fylke Vegreferanse.vegstatus
    MATCH_STRATEGY = Match Selected Attributes
    CNT_ATTR = _match_id
    BLANK_AND_MISSING_DIFFER = No
    MATCH = FULL
    LENIENT_MATCH = No
    SINGLE_MATCHED -> Aggregator
    NOT_MATCHED -> Aggregator
Aggregator
    AGGREGATE_TYPE = Homogeneous Collection (If Possible)
    GROUP_BY = Vegreferanse.kommune NVDB_ID vegklasse merknad Vegreferanse.hovedparsell Vegreferanse.vegkategori Vegreferanse.vegstatus Vegreferanse.fylke Vegreferanse.vegnummer
    MODE = Geometry - Assemble One Level
    ACCUM_ATTRS_NAME = No
    SEP = ,
    ORDERED = No
    AGGREGATE -> Output (output)
Output (output)

FME custom transformer LesVegreferanseobjekter
Leser vegreferanseobjekter fra NVDB-API, basert på utvalgskriterie

Parameters:
- HREF = @Value(href)   # href

Input (input)
    -> NVDB_Leser_3 [_Input]
NVDB_Leser_3
    NESTE.HREF = @Value(href)
    -> AttributeExposer
Note: Tvinger fram vegreferanseegenskaper
AttributeExposer
    ATTR_LIST = 4591,4592,4566,4568,4569,4567
    -> AttributeManager_2
AttributeManager_2
    ATTR_TABLE:
      RENAME_SET_VALUE 4591 > fylkesnummer
      RENAME_SET_VALUE 4592 > kommunenummer
      RENAME_SET_VALUE 4566 > vegkategori
      RENAME_SET_VALUE 4568 > vegnummer
      RENAME_SET_VALUE 4569 > hovedparsell
      RENAME_SET_VALUE 4567 > vegstatus
    -> AttributeKeeper
AttributeKeeper
    KEEP_ATTRS = fylkesnummer,vegstatus,vegnummer,hovedparsell,kommunenummer,vegkategori
    -> Aggregator
Aggregator
    AGGREGATE_TYPE = Homogeneous Collection (If Possible)
    GROUP_BY = fylkesnummer vegstatus vegnummer hovedparsell kommunenummer vegkategori
    MODE = Geometry - Assemble One Level
    ACCUM_ATTRS_NAME = No
    SEP = ,
    ORDERED = No
    AGGREGATE -> BoundsExtractor
BoundsExtractor
    XMAX = _xmax
    ZMAX = _zmax
    ZMIN = _zmin
    YMAX = _ymax
    XMIN = _xmin
    YMIN = _ymin
    -> AttributeValueMapper
AttributeValueMapper
    LUT = 5492,E,5493,R,5494,F,5495,K,5496,P,5497,S
    SRC = vegkategori
    DEFAULT_VALUE = Ukjent
    VAL_ATTR = _vk
    DIRECTION = Forward (Source To Destination)
    -> Output (output)
Output (output)

FME custom transformer NVDB_Leser
Leser og tolker data fra NVDB-API

Parameters:
- NESTE.HREF = @Value(neste.href)   # neste.href

_Input (input)
    -> HTTPCaller_2
Loop (input)
    -> HTTPCaller_2
HTTPCaller_2
    TARGET_URL = @Value(neste.href)
    TARGET_ATTR = _url_contents
    USE_COOKIES = No
    TRANSFER_TIMEOUT_LENGTH = 90
    CUSTOM_HEADERS = Accept;application/vnd.vegvesen.nvdb-v2+xml
    HTTP_METHOD = GET
    VERIFY_SSL_CERTIFICATES = Yes
    CONNECTION_TIMEOUT_LENGTH = 60
    FOLLOW_REDIRECTS = Yes
    SAVE_FILE = Attribute
    ERROR_ATTR = _error
    STATUS_CODE_ATTR = _http_status_code
    TARGET_ATTR_ENCODING = auto-detect
    RESPONSE_HEADER_LIST_ATTR = _headers
    -> XMLFragmenter_2
    -> XMLFragmenter
Note: Deler opp i en XML pr vegobjekt
XMLFragmenter
    XML_SOURCE_TYPE = Attribute with XML document
    EMBEDDED_EXPRESSIONS = vegobjekt
    ATTRIBUTE_XML = _url_contents
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    FEATURE_TYPES_FORMAT_NAME = XML
    NEW_ATTRIBUTES = id geometri.wkt
    FRAGMENTS -> AttributeRemover
AttributeRemover
    REMOVE_ATTRS = _url_contents
    -> NVDBTranslator
Note: Oversetter fra NVDB-API-XML
NVDBTranslator: PythonCaller
    PYTHONSOURCE:
      import fme
      import fmeobjects

      def extractNVDB_XML(feature):

          ns='vegvesen.no.nvdb' #FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          v= feature.getAttribute('lokasjon.kommuner.kommune')
          if v != None:
              feature.setAttribute('lokasjon.kommune',v)

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute('lineærPosisjon{%d}.LineærPosisjonStrekning.nettverkselement.xlink_href' % i, 'Veglenker.gml#' + ns + '.rl.' + v)
                          v = str(feature.getAttribute('lokasjon.stedfestinger.stedfesting.fra_posisjon'))
                          if v != 'None':
                              feature.setAttribute('lineærPosisjon{%d}.LineærPosisjonStrekning.fraPosisjon' % i, v)
                          v = str(feature.getAttribute('lokasjon.stedfestinger.stedfesting.til_posisjon'))
                          if v != 'None':
                              feature.setAttribute('lineærPosisjon{%d}.LineærPosisjonStrekning.tilPosisjon' % i, v)

                          v = str(feature.getAttribute('lokasjon.stedfestinger.stedfesting.sideposisjon'))
                          if v != 'None':
                              feature.setAttribute('lineærPosisjon{%d}.LineærPosisjonStrekning.sideposisjon' % i, v)

                          v = str(feature.getAttribute('lokasjon.stedfestinger.stedfesting.retning'))
                          if v != 'None':
                              feature.setAttribute('lineærPosisjon{%d}.LineærPosisjonStrekning.retning' % i, v.lower())
                          feature.setAttribute('lineærPosisjon{%d}.LineærPosisjonStrekning.lineærReferanseMetode' % i, 'normalisert')

                      else:
                          # Punktstedfesting
                          v = str(feature.getAttribute('lokasjon.stedfestinger.stedfesting.veglenkeid'))
                          if v != 'None':
                              feature.setAttribute('lineærPosisjon{%d}.LineærPosisjonPunkt.nettverkselement.xlink_href' % i, 'Veglenker.gml#' + ns + '.rl.' + v)

                          v = str(feature.getAttribute('lokasjon.stedfestinger.stedfesting.posisjon'))
                          if v != 'None':
                              feature.setAttribute('lineærPosisjon{%d}.LineærPosisjonPunkt.posisjon' % i, v)

                          v = str(feature.getAttribute('lokasjon.stedfestinger.stedfesting.sideposisjon'))
                          if v != 'None':
                              feature.setAttribute('lineærPosisjon{%d}.LineærPosisjonPunkt.sideposisjon' % i, v)
                          feature.setAttribute('lineærPosisjon{%d}.LineærPosisjonPunkt.lineærReferanseMetode' % i, 'normalisert')

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute('lineærPosisjon{%d}.LineærPosisjonStrekning.nettverkselement.xlink_href' % i, 'Veglenker.gml#' + ns + '.rl.' + v)

                      v = str(feature.getAttribute('lokasjon.stedfestinger.stedfesting{%d}.fra_posisjon' % i))
                      if v != 'None':
                          feature.setAttribute('lineærPosisjon{%d}.LineærPosisjonStrekning.fraPosisjon' % i, v)

                      v = str(feature.getAttribute('lokasjon.stedfestinger.stedfesting{%d}.til_posisjon' % i))
                      if v != 'None':
                          feature.setAttribute('lineærPosisjon{%d}.LineærPosisjonStrekning.tilPosisjon' % i, v)

                      v = str(feature.getAttribute('lokasjon.stedfestinger.stedfesting{%d}.sideposisjon' % i))
                      if v != 'None':
                          feature.setAttribute('lineærPosisjon{%d}.LineærPosisjonStrekning.sideposisjon' % i, v)

                      v = str(feature.getAttribute('lokasjon.stedfestinger.stedfesting{%d}.retning' % i))
                      if v != 'None':
                          feature.setAttribute('lineærPosisjon{%d}.LineærPosisjonStrekning.retning' % i, v.lower())
                      feature.setAttribute('lineærPosisjon{%d}.LineærPosisjonStrekning.lineærReferanseMetode' % i, 'normalisert')

                  else:
                      # Punktstedfesting
                      v = str(feature.getAttribute('lokasjon.stedfestinger.stedfesting{%d}.veglenkeid' % i))
                      if v != 'None':
                          feature.setAttribute('lineærPosisjon{%d}.LineærPosisjonPunkt.nettverkselement.xlink_href' % i, 'Veglenker.gml#' + ns + '.rl.' + v)

                      v = str(feature.getAttribute('lokasjon.stedfestinger.stedfesting{%d}.posisjon' % i))
                      if v != 'None':
                          feature.setAttribute('lineærPosisjon{%d}.LineærPosisjonPunkt.posisjon' % i, v)

                      v = str(feature.getAttribute('lokasjon.stedfestinger.stedfesting{%d}.sideposisjon' % i))
                      if v != 'None':
                          feature.setAttribute('lineærPosisjon{%d}.LineærPosisjonPunkt.sideposisjon' % i, v)
                      feature.setAttribute('lineærPosisjon{%d}.LineærPosisjonPunkt.lineærReferanseMetode' % i, 'normalisert')

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  feature.setAttribute('vegreferanse{%d}.Vegreferanse.vegkategori' % i, v)
                  feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg vegreferanse{} lineærPosisjon{} lokasjon.kommune
    -> AttributeFilter
AttributeFilter
    ATTR_VALUES = <EMPTY>,<MISSING>,<NULL>,<UNFILTERED>
    ATTR_NAME = geometri
    <EMPTY> -> EmptyGeometry
    <MISSING> -> MissingGeometry
    <NULL> -> NullGeometry
    <UNFILTERED> -> GeometryReplacer
EmptyGeometry: Inspector
MissingGeometry: Inspector
NullGeometry: Inspector
Note: Geometri
GeometryReplacer
    SOURCE = @Value(geometri)
    REMOVE_ATTRIBUTE = Yes
    KIND_LONG = OGC Well Known Text
    OGC_WKT_PRECISION_DISPLAY = 64-bit
    -> CoordinateSystemSetter
    -> CoordinateSystemSetter_2
CoordinateSystemSetter
    COORDSYS = @Value(epsg)
    -> Deaggregator
CoordinateSystemSetter_2 [off]
    COORDSYS = EPSG:25833
    -> Deaggregator
XMLFragmenter_2
    XML_SOURCE_TYPE = Attribute with XML document
    EMBEDDED_EXPRESSIONS = side/metadata
    ATTRIBUTE_XML = _url_contents
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    FEATURE_TYPES_FORMAT_NAME = XML
    NEW_ATTRIBUTES = returnert neste.href
    FRAGMENTS -> TestFilter
TestFilter
    TEST_LIST = BOOL_OP,OR,COMPOSITE_TEST,<Unused>,TEST_CLAUSE,"TEST @Value(returnert) != 0",Flere
    DEFAULT_VALUE = <UNFILTERED>
    Flere -> Loop (output)
Loop (output)

Bookmark: Splitter multigeometrier
Deaggregator
    PARENT_ID_ATTR = _hierarchy_parent_id
    LIST_ATTR_MODE_LOOKUP = LEAN
    SPLIT_COMPOSITES = No
    GEOM_NAME_FIELD = _geometry_name
    ID_SELECTION = ID and Parent ID
    ID_ATTR = _hierarchy_id
    PART_NUMBER_FIELD = _part_number
    EXPLODE_INSTANCES = No
    CHILD_ID_ATTR = _hierarchy_child_id_list
    COPY_ATTR = Every Node
    MODE = Flatten One Level
    DEAGGREGATED -> NullAttributeMapper
NullAttributeMapper
    NULL_TREATMENT = New Value
    ATTRLIST = _part_number
    ATTRCHOICE = Selected Attributes
    SOURCE_ATTR_VAL = Null Empty "Missing (Selected Attributes Only)"
    NEW_VALUE = 0
    -> StringConcatenator
StringConcatenator
    ACTION = Create New Attribute
    PARM_LINE = @Value(gml_id)_@Value(_part_number)
    VAL_ATTR = gml_id
    -> Output (output)
Output (output)
