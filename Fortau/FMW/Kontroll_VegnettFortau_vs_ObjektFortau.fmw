FME workspace Kontroll_VegnettFortau_vs_ObjektFortau.fmw

Parameters:
- MinKnr = 1800   # Fra og med kommunenummer
- MaxKnr = 2099   # Til og med kommunenummer
- dataFolder = O:\1\Res\16080 Geodata\Fagområde Vegnett\Vegnett spesialistfunksjon\Feil og kvalitetskontroller i NVDB\FME-kontroller\Fortau\Data   # Mappe med resultatfiler
- coordsys = EPSG:25833   # Koordinatsystem
- CONNECTION_FILE = C:\DATA\PTNE-sde_tne_read@svvkartp.vegvesen.no.sde   # Connection File
- xfmap_api = O:\1\Res\16080 Geodata\Fagområde Vegnett\Vegnett spesialistfunksjon\Feil og kvalitetskontroller i NVDB\FME-kontroller\Felles\API_Mapping.xmp   # xfMap for API-mapping

Writers:
- XLSXW_1: XLSXW to $(dataFolder)
- SPATIALITE_1: SPATIALITE to $(dataFolder) in EPSG:25833

AttributeManager_2
    ATTR_TABLE:
      REMOVE OBJECTID
      REMOVE _headers{}.name
      REMOVE _headers{}.value
      REMOVE _url_contents
      REMOVE _http_status_code
      REMOVE kode
    -> 1_VegnettFortau (writer XLSXW_1)
    -> 1_VegnettFortau
    -> 1_vegnettfortau (writer SPATIALITE_1)
1_VegnettFortau: Inspector
1_VegnettFortau (writer XLSXW_1)
    attributes: fylkeNr auto(20), kommuneNr auto(20), vegKategori auto(20), vegStatus auto(20), vegNummer auto(20), hovedParsell auto(20), meterVerdi auto(20), RefLink auto(20), fraPosisjon auto(20), tilPosisjon auto(20)
1_vegnettfortau (writer SPATIALITE_1)
    attributes: fylkenr string(200), kommunenr string(200), vegkategori string(200), vegstatus string(200), vegnummer string(200), hovedparsell string(200), meterverdi string(200), reflink string(200), fraposisjon string(200), tilposisjon string(200)
AttributeManager_OUTPUT_-__EventOverlayer_2_Event_table_B: Junction
    -> EventOverlayer_2 [Event_table_B]
    -> AttributeManager_OUTPUT_-__EventOverlayer_2_Event_table_B_Output_-__EventOverlayer_3_Event_table_B
Note: Workspace som analyserer overlapp mellom temakode fortau i vegnettet og objekttype Fortau. / I utfilene er vegreferanser angitt for strekningen sin startposisjon, mens posisjoner på referanselenkene er gitt som fra- og tilposisjoner. / Historikk: / 20160706 Knut Jetlund / Oppretta workspace,finner: / Veglenke med temakode fortau (7046) / Overlapp mellom objekttype Fortau og temakode fortau på vegnett (dvs Fortau på GS-veg m/type fortau) / Objekttype Fortau på GS-veg-lenker (dvs Fortau på GS-veg) / Objekttype Fortau der det er nærliggende lenker med GS-veg
AttributeManager_6
    ATTR_TABLE:
      REMOVE _creation_instance
      REMOVE _headers{}.name
      REMOVE _headers{}.value
      REMOVE _response_body
      REMOVE _http_status_code
      REMOVE _element_index
      REMOVE kommunenavn
      REMOVE kommunenummer
      REMOVE fylkesnummer
      REMOVE region
      REMOVE _url_contents
      REMOVE egengeometri
      REMOVE felt
      REMOVE _xml_feature_count_
      REMOVE fme_feature_type
      REMOVE _xml_source_
      RENAME_SET_VALUE Vegreferanse.vegkategori > vegkategori
      RENAME_SET_VALUE Vegreferanse.vegnummer > vegnummer
      RENAME_SET_VALUE Vegreferanse.vegstatus > vegstatus
      RENAME_SET_VALUE Vegreferanse.hovedParsell > hovedparsell
      RENAME_SET_VALUE Vegreferanse.veglenkeMeterFra > meterFra
      RENAME_SET_VALUE Vegreferanse.veglenkeMeterTil > meterTil
      RENAME_SET_VALUE Vegreferanse.fylke > fylkeNr
      RENAME_SET_VALUE Vegreferanse.kommune > kommuneNr
      RENAME_SET_VALUE lineærtObjektIdentifikasjon.Identifikasjon.lokalId > RefLink
    -> AttributeManager_6_OUTPUT
AttributeManager_6_OUTPUT: Junction
    -> AttributeManager_5
    -> TestFilter_2
AttributeManager_5
    ATTR_TABLE:
      REMOVE vegkategori
      REMOVE vegnummer
      REMOVE vegstatus
      REMOVE fylkeNr
      REMOVE kommuneNr
      REMOVE hovedparsell
      REMOVE meterFra
      REMOVE meterTil
    -> EventOverlayer [Event_table_B]
AttributeManager_4
    ATTR_TABLE:
      REMOVE OBJECTID
      REMOVE RoadLinkID
      RENAME_SET_VALUE FromVal > fraPosisjon
      RENAME_SET_VALUE ToVal > tilPosisjon
      REMOVE _SegId
      REMOVE _headers{}.name
      REMOVE _headers{}.value
      REMOVE _url_contents
      REMOVE _http_status_code
    -> 2_VegnettFortau_ObjekttypeForta (writer XLSXW_1)
    -> 2_VegnettFortau_ObjekttypeForta
    -> 2_vegnettfortau_objekttypeforta (writer SPATIALITE_1)
2_VegnettFortau_ObjekttypeForta: Inspector
    TACKATTRS = fylkeNr
2_VegnettFortau_ObjekttypeForta (writer XLSXW_1)
    attributes: fylkeNr auto(20), kommuneNr auto(20), vegKategori auto(20), vegStatus auto(20), vegNummer auto(20), hovedParsell auto(20), meterVerdi auto(20), RefLink auto(20), fraPosisjon auto(20), tilPosisjon auto(20), sideposisjon auto(20), kode auto(20), NVDB_ID auto(20)
2_vegnettfortau_objekttypeforta (writer SPATIALITE_1)
    attributes: fylkenr string(200), kommunenr string(200), vegkategori string(200), vegstatus string(200), vegnummer string(200), hovedparsell string(200), meterverdi string(200), reflink string(200), fraposisjon string(200), tilposisjon string(200), sideposisjon string(200), kode string(200), nvdb_id string(200)
TestFilter_2
    TEST_LIST = BOOL_OP,OR,COMPOSITE_TEST,<Unused>,TEST_CLAUSE,"TEST @Value(vegstatus) IN G, U, H, Q",GS-veg
    DEFAULT_VALUE = <UNFILTERED>
    GS-veg -> TestFilter_2_GS-veg
    <UNFILTERED> -> GeometryExtractor
TestFilter_2_GS-veg: Junction
    -> FeatureMerger_2 [REQUESTOR]
    -> EventOverlayer_2 [Event_table_A]
GeometryExtractor
    ATTR = _geometry
    OGC_WKT_PRECISION_DISPLAY = Shortened 64-bit
    PREFER_POLYGON_OVER_SURFACE = No
    OGEOSMS_URL_PREFIX = http://maps.google.com/?q=
    LETTERING = WGS84
    KIND_LONG = FME Binary
    ELLIPSOID_NAME = WGS84
    MSSQL_FORMAT_CHOICE = Geometry
    OMIT_NAMESPACES_DISPLAY = No
    LEVELS_ATTR = _levels
    PRECISION = 0
    OGCVERSION = 1.1
    REMOVE_GEOMETRY = No
    GEOHASH_PRECISION_DISPLAY = ~9.3 mm (12 characters)
    -> Bufferer

Bookmark: Utvalg av kommuner
Creator
    NUM = 1
    GEOMTYPE = Geometry Object
    CREATED -> HTTPCaller
HTTPCaller
    STATUS_CODE_ATTR = _http_status_code
    ERROR_ATTR = _error
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/omrader/kommuner/
    USE_COOKIES = No
    TARGET_ATTR_ENCODING = auto-detect
    TRANSFER_TIMEOUT_LENGTH = 90
    TARGET_ATTR = _response_body
    -> XMLFlattener
XMLFlattener
    NEW_ATTRIBUTES = kommune{}
    FEATURE_TYPES_FORMAT_NAME = XML
    XML_SOURCE_TYPE = Attribute with XML document
    ATTRIBUTE_XML = _response_body
    EMBEDDED_EXPRESSIONS = kommuner
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> ListExploder
ListExploder
    ATTR_ACCUM_MODE = Merge Incoming List
    LIST_ATTR = kommune{}
    INDEX_ATTR = _element_index
    ATTR_CONFLICT_RES = Use Incoming List
    ELEMENTS -> AttributeExposer
AttributeExposer
    ATTR_LIST = navn,nummer,fylke,region
    -> TestFilter
TestFilter
    TEST_LIST:
      BOOL_OP,AND,COMPOSITE_TEST,<Unused>,TEST_CLAUSE,"TEST @Value(nummer) >= $(MinKnr)
      TEST @Value(nummer) <= $(MaxKnr)",UtvalgteKommuner
    DEFAULT_VALUE = <UNFILTERED>
    UtvalgteKommuner -> AttributeManager_3
AttributeManager_3
    ATTR_TABLE:
      REMOVE kommune
      RENAME_SET_VALUE navn > kommunenavn
      RENAME_SET_VALUE nummer > kommunenummer
      RENAME_SET_VALUE fylke > fylkesnummer
    -> HTTPCaller_4
    -> HTTPCaller_2

Bookmark: Leser Kommuneflate fra NVDB API
Note: Henter objekter fra NVDB-API
HTTPCaller_4
    STATUS_CODE_ATTR = _http_status_code
    ERROR_ATTR = _error
    CUSTOM_HEADERS = Accept;application/vnd.vegvesen.nvdb-v1+xml
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/sok?kriterie={"lokasjon":{"kommune":["@Value(kommunenummer)"]},"objektTyper":[{"id":536,"antall":"100000","filter":[]}]}
    USE_COOKIES = No
    TARGET_ATTR_ENCODING = auto-detect
    TRANSFER_TIMEOUT_LENGTH = 90
    TARGET_ATTR = _url_contents
    -> XMLFeatureMapper_3
Note: Tolker XML
XMLFeatureMapper_3
    ATTRIBUTE_XML = _url_contents
    XML_SOURCE_NAME = _xml_source_
    MERGE_ATTRS = Yes
    FEATURE_COUNT_PER_XML = _xml_feature_count_
    SINGLE_XFMAP = $(xfmap_api)
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt vegreferanse{}.fylke vegreferanse{}.kommune NVDB_ID
    XML_INPUT_TYPE = Attribute with XML document
    FEATURE_TYPE_ATTR = fme_feature_type
    CONFIGURATION_TYPE = Single xfMap file
    MAPPED -> GeometryReplacer_3
Note: Tildeler geometri
GeometryReplacer_3
    REMOVE_ATTRIBUTE = Yes
    KIND_LONG = OGC Well Known Text
    SOURCE = @Value(geometriUtm33)
    OGC_WKT_PRECISION_DISPLAY = 64-bit
    -> CoordinateSystemSetter_3
CoordinateSystemSetter_3
    COORDSYS = $(coordsys)
    -> Dissolver_2
Dissolver_2
    NO_OVRLP = No
    GROUP_BY = kommunenummer
    CONNECT_Z_MODE = First Wins
    ACCUM_INPUT_ATTRS = Drop Incoming Attributes
    AREA -> DonutHoleExtractor
DonutHoleExtractor
    OUTERSHELL -> TimeStamper_2

Bookmark: Finner overlapp mellom fortau i vegnett og objekttype fortau
TimeStamper_2
    TIME_ATTR = _timestamp
    FMT = FME Date (^Y^m^d)
    -> StringConcatenator_5
StringConcatenator_5
    PARM_LINE = TO_DATE>@Value(_timestamp)
    ACTION = Create New Attribute
    VAL_ATTR = _where
    -> FeatureReader_3 [INITIATOR]
Note: Leser vegnettsgeometri med type=fortau (7046) fra TNE
FeatureReader_3
    GEODATABASE_SDE_RESOLVE_DOMAINS = no
    FEATURETYPES = SDE_TNE.TNE_CurveSegment
    ATTR_ACCUM_MODE = Only Use Result
    GEODATABASE_SDE_FEATURE_READ_MODE = Features
    GEODATABASE_SDE_MERGE_FEAT_LINKED_ANNOS = no
    GEODATABASE_SDE_CONNECTION_FILE = $(CONNECTION_FILE)
    GEODATABASE_SDE_TRANSLATE_SPATIAL_DATA_ONLY = no
    GEODATABASE_SDE_SPLIT_COMPLEX_EDGES = no
    GEODATABASE_SDE_SPLIT_COMPLEX_ANNOS = no
    GEODATABASE_SDE_REMOVE_TABLE_QUALIFIER = NO
    GEODATABASE_SDE_CREDENTIALS_OVERRIDE = NO
    GEODATABASE_SDE_SPLIT_MULTI_PART_ANNOS = no
    GEODATABASE_SDE_SEARCH_ORDER = SPATIAL_FIRST
    ATTRIBUTES = SDE_TNE.TNE_CurveSegment,"OBJECTID,REFLINK_OID,FROM_DATE,TO_DATE,FROM_MEASURE,TO_MEASURE,SEG_DATE,LENGTH,CLASS_CODE,OBJECT_CODE,MEDIUM,QUALITY_METHOD,QUALITY_ACCURACY,QUALITY_VISIBILITY,QUALITY_METHOD_HEIGHT,QUALITY_ACCURACY_HEIGHT,QUALITY_TOLERANCE,MUNICIPALITY,SHAPE.LEN"
    COMBINE_GEOM = Use Result
    GEODATABASE_SDE_CHECK_SIMPLE_GEOM = no
    GEODATABASE_SDE_ALIAS_MODE = NONE
    OUTPUT_FEATURES_DISPLAY = Schema and Data Features
    GEODATABASE_SDE_SEARCH_METHOD = GEODB_INTERSECTS
    GEODATABASE_SDE_VERSION_TYPE = Version from SDE Connection
    GEODATABASE_SDE_USE_SEARCH_ENVELOPE = NO
    FORMAT = GEODATABASE_SDE
    GEODATABASE_SDE_READ_VERSION_DIFFERENCES = NO
    WHERE = @Value(_where)
    GEODATABASE_SDE_CACHE_MULTIPATCH_TEXTURES = yes
    SUPPORTED_SPATIAL_INTERACTIONS = ENVELOPE_INTERSECT%ENVELOPE_INTERSECT%INTERSECTS%CONTAINS%CROSSES%DISJOINT%EQUALS%OVERLAPS%TOUCHES%WITHIN
    GEODATABASE_SDE_QUERY_FEATURE_TYPES_FOR_MERGE_FILTERS = Yes
    GEODATABASE_SDE_RESOLVE_SUBTYPE_NAMES = yes
    GEODATABASE_SDE_IGNORE_RELATIONSHIP_INFO = yes
    GEODATABASE_SDE_CLIP_TO_ENVELOPE = NO
    GEODATABASE_SDE_PERSISTENT_CONNECTION = no
    INTERACT = Intersects
    GEODATABASE_SDE_IGNORE_NETWORK_INFO = yes
    SDE_TNE.TNE_CurveSegment -> AttributeManager
AttributeManager
    ATTR_TABLE:
      RENAME_SET_VALUE REFLINK_OID > RefLink
      REMOVE FROM_DATE
      REMOVE TO_DATE
      RENAME_SET_VALUE FROM_MEASURE > fraPosisjon
      RENAME_SET_VALUE TO_MEASURE > tilPosisjon
      REMOVE SEG_DATE
      REMOVE LENGTH
      RENAME_SET_VALUE CLASS_CODE > kode
      REMOVE OBJECT_CODE
      REMOVE MEDIUM
      REMOVE QUALITY_METHOD
      REMOVE QUALITY_ACCURACY
      REMOVE QUALITY_VISIBILITY
      REMOVE QUALITY_METHOD_HEIGHT
      REMOVE QUALITY_ACCURACY_HEIGHT
      REMOVE QUALITY_TOLERANCE
      REMOVE MUNICIPALITY
      REMOVE SHAPE.LEN
    -> TestFilter_4
    -> AttributeManager_OUTPUT_-__EventOverlayer_2_Event_table_B
TestFilter_4
    TEST_LIST = BOOL_OP,OR,COMPOSITE_TEST,<Unused>,TEST_CLAUSE,"TEST @Value(kode) = 7046",7046
    DEFAULT_VALUE = <UNFILTERED>
    7046 -> HTTPCaller_5
    7046 -> FeatureMerger [REQUESTOR]
    7046 -> EventOverlayer [Event_table_A]
Note: Finner overlappende segmenter
EventOverlayer
    FromVal = @Value(fraPosisjon)
    ToVal = @Value(tilPosisjon)
    RoadLinkID = @Value(RefLink)
    Common_Segments -> AttributeExposer_2
AttributeExposer_2
    ATTR_LIST = sideposisjon,OBJECTID
    -> FeatureMerger [SUPPLIER]
Note: kobler segmentene til vegnett
FeatureMerger
    IGNORE_NULLS = No
    SUPPLIERS_FIRST = No
    LIST_NAME = overlapList
    MERGE_TYPE = Attributes Only
    JOIN_KEYS = @Value(OBJECTID) @Value(OBJECTID) AUTO
    REJECT_NULL_MISSING_KEYS = No
    ATTR_ACCUM_MODE = Merge Supplier
    ATTR_CONFLICT_RES = Use Requestor
    PROCESS_DUPS = No
    MERGED -> ListDuplicateRemover
ListDuplicateRemover
    SRC_LIST = overlapList{}.sideposisjon
    -> ListConcatenator
Note: Lager liste over sideposisjoner
ListConcatenator
    SEP = ,
    VAL_ATTR = sideposisjon
    LIST_ATTR = overlapList{}.sideposisjon
    DROP_EMPTY_PARTS = No
    -> AttributeRemover
AttributeRemover
    LIST_ATTRS = overlapList{} overlapList{}.FromVal overlapList{}.OBJECTID overlapList{}.RefLink overlapList{}.RoadLinkID overlapList{}.ToVal overlapList{}._SegId overlapList{}.fraPosisjon overlapList{}.sideposisjon overlapList{}.tilPosisjon overlapList{}.vegreferanse{} overlapList{}.vegreferanse{}.fylke overlapList{}.vegreferanse{}.hovedParsell overlapList{}.vegreferanse{}.kommune overlapList{}.vegreferanse{}.vegkategori overlapList{}.vegreferanse{}.veglenkeMeterFra overlapList{}.vegreferanse{}.veglenkeMeterTil overlapList{}.vegreferanse{}.vegnummer overlapList{}.vegreferanse{}.vegstatus vegreferanse{} vegreferanse{}.fylke vegreferanse{}.hovedParsell vegreferanse{}.kommune vegreferanse{}.vegkategori vegreferanse{}.veglenkeMeterFra vegreferanse{}.veglenkeMeterTil vegreferanse{}.vegnummer vegreferanse{}.vegstatus
    REMOVE_ATTRS = meterTil,vegstatus,meterFra,hovedparsell,vegkategori,vegnummer
    -> HTTPCaller_3

Bookmark: Finner vegreferanse for start-posisjon
Note: Henter vegreferanse fra NVDB-API
HTTPCaller_5
    STATUS_CODE_ATTR = _http_status_code
    ERROR_ATTR = _error
    CUSTOM_HEADERS = Accept;application/vnd.vegvesen.nvdb-v1+xml
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/vegreferanse/lenke?id=@Value(RefLink)&posisjon=@Value(fraPosisjon)
    USE_COOKIES = No
    TARGET_ATTR_ENCODING = auto-detect
    TRANSFER_TIMEOUT_LENGTH = 90
    TARGET_ATTR = _url_contents
    -> XMLFlattener_3
XMLFlattener_3
    NEW_ATTRIBUTES = fylkeNr kommuneNr vegKategori vegStatus vegNummer hovedParsell meterVerdi
    FEATURE_TYPES_FORMAT_NAME = XML
    XML_SOURCE_TYPE = Attribute with XML document
    ATTRIBUTE_XML = _url_contents
    EMBEDDED_EXPRESSIONS = vegReferanseSok
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeManager_2

Bookmark: Leser Vegreferanselenker med status G, U, H eller Q rundt fortauene
AttributeManager_OUTPUT_-__EventOverlayer_2_Event_table_B_Output_-__EventOverlayer_3_Event_table_B: Junction
    -> EventOverlayer_4 [Event_table_B]
Bufferer
    CAP_STYLE = None
    OFFSET = 20
    INTERP_SEGMENTS = 8
    BUFFERED -> Bufferer_BUFFERED_-__FeatureMerger_3_REQUESTOR
    BUFFERED -> BoundsExtractor
Bufferer_BUFFERED_-__FeatureMerger_3_REQUESTOR: Junction
    -> GeometryReplacer
    -> Clipper [CLIPPER]
GeometryReplacer
    REMOVE_ATTRIBUTE = Yes
    KIND_LONG = FME Binary
    SOURCE = @Value(_geometry)
    -> FeatureMerger_3 [REQUESTOR]
BoundsExtractor
    ZMAX = _zmax
    XMAX = _xmax
    YMAX = _ymax
    XMIN = _xmin
    ZMIN = _zmin
    YMIN = _ymin
    -> HTTPFetcher_3
Note: Henter objekter fra NVDB-API
HTTPFetcher_3
    TARGET_ATTR = _url_contents
    USE_COOKIES = No
    REQUEST_HEADER:
      GET /vegobjekter HTTP/1.1
      Accept: application/vnd.vegvesen.nvdb-v1+xml
    TARGET_URL = https://www.vegvesen.no/nvdb/api/sok?kriterie={"lokasjon":{bbox:"@Value(_xmin),@Value(_ymin),@Value(_xmax),@Value(_ymax)"},"objektTyper":[{"id":532,"filter":[{"typeId":4567,"operator":"=","verdi":[12159,12160,12983,12986]}],"antall":10000}]}
    FOLLOW_REDIRECTS = Yes
    ERROR_ATTR = _error
    PROXY_AUTH_METHOD = Basic
    RESPONSE_HEADER_LIST_ATTR = _headers
    TRANSFER_TIMEOUT_LENGTH = 90
    STATUS_CODE_ATTR = _http_status_code
    CONNECTION_TIMEOUT_LENGTH = 60
    SAVE_FILE = No
    VERIFY_SSL_CERTIFICATES = Yes
    -> XMLFeatureMapper_4
Note: Tolker XML
XMLFeatureMapper_4
    ATTRIBUTE_XML = _url_contents
    XML_SOURCE_NAME = _xml_source_
    MERGE_ATTRS = Yes
    FEATURE_COUNT_PER_XML = _xml_feature_count_
    SINGLE_XFMAP = $(xfmap_api)
    NEW_ATTRIBUTES = egengeometri geometriUtm33 vegreferanse{}.Vegreferanse.vegkategori vegreferanse{}.Vegreferanse.vegnummer vegreferanse{}.Vegreferanse.vegstatus vegreferanse{}.Vegreferanse.hovedParsell vegreferanse{}.Vegreferanse.veglenkeMeterFra vegreferanse{}.Vegreferanse.veglenkeMeterTil lineærPosisjon{}.lineærtObjektIdentifikasjon.Identifikasjon.lokalId lineærPosisjon{}.fraPosisjon lineærPosisjon{}.tilPosisjon lineærPosisjon{}.felt vegreferanse{}.Vegreferanse.fylke vegreferanse{}.Vegreferanse.kommune
    XML_INPUT_TYPE = Attribute with XML document
    FEATURE_TYPE_ATTR = fme_feature_type
    CONFIGURATION_TYPE = Single xfMap file
    MAPPED -> GeometryReplacer_4
Note: Tildeler geometri
GeometryReplacer_4
    REMOVE_ATTRIBUTE = Yes
    KIND_LONG = OGC Well Known Text
    SOURCE = @Value(geometriUtm33)
    OGC_WKT_PRECISION_DISPLAY = 64-bit
    -> CoordinateSystemSetter_4
Note: Setter koordinatsystem
CoordinateSystemSetter_4
    COORDSYS = $(coordsys)
    -> DuplicateFilter
Note: Fjerner duplikater
DuplicateFilter
    INPUT_ORDERED_CHOICE = No
    KEYATTR = NVDB_ID
    UNIQUE -> AttributeKeeper
AttributeKeeper
    -> Clipper [CLIPPEE]
Note: Avgrenser vegreferanselenkene til buffer
Clipper
    ATTR_ACCUM_MODE = Merge Clipper
    CLIPPED_ATTR = _clipped
    BOUNDARY_CASES = Treat as Inside
    CLIP_TYPE = Multiple Clippers
    ATTR_CONFLICT_RES = Use Clipper
    CREATE_AGGREGATES = Yes
    CONNECT_Z_MODE = First Wins
    PRESERVE_CLIPPEE_EXTENTS = No
    LINES_AS_SEGMENTS = No
    INSIDE -> CoordinateExtractor
Note: Finner overlappende kurvesegmenter for de nærliggende vegreferanseobjektene
EventOverlayer_4
    FromVal = @Value(fraPosisjon)
    ToVal = @Value(tilPosisjon)
    RoadLinkID = @Value(RefLink)
    Common_Segments -> AttributeExposer_5
    Only_A -> AttributeExposer_5
AttributeExposer_5
    ATTR_LIST = NVDB_ID,kode
    -> AttributeManager_8
AttributeManager_8
    ATTR_TABLE:
      REMOVE RoadLinkID
      REMOVE FromVal
      REMOVE ToVal
      REMOVE tilPosisjon
      REMOVE RefLink
      REMOVE fraPosisjon
      REMOVE vegkategori
      REMOVE vegnummer
      REMOVE vegstatus
      REMOVE fylkeNr
      REMOVE kommuneNr
      REMOVE sideposisjon
      REMOVE _SegId
      REMOVE hovedparsell
      REMOVE meterFra
      REMOVE meterTil
      REMOVE _geometry
    -> FeatureMerger_3 [SUPPLIER]
Note: kobler segmentene til fortausobjektene
FeatureMerger_3
    IGNORE_NULLS = No
    SUPPLIERS_FIRST = No
    LIST_NAME = overlapList
    MERGE_TYPE = Attributes Only
    JOIN_KEYS = @Value(NVDB_ID) @Value(NVDB_ID) AUTO
    REJECT_NULL_MISSING_KEYS = No
    ATTR_ACCUM_MODE = Merge Supplier
    ATTR_CONFLICT_RES = Use Requestor
    PROCESS_DUPS = No
    MERGED -> ListDuplicateRemover_3
ListDuplicateRemover_3
    SRC_LIST = overlapList{}.kode
    -> ListConcatenator_3
Note: Lager liste over temakoder
ListConcatenator_3
    SEP = ,
    VAL_ATTR = kode
    LIST_ATTR = overlapList{}.kode
    DROP_EMPTY_PARTS = No
    -> AttributeRemover_3
AttributeRemover_3
    LIST_ATTRS = _relationships{} overlapList{} overlapList{}.FromVal overlapList{}.NVDB_ID overlapList{}.OBJECTID overlapList{}.RefLink overlapList{}.RoadLinkID overlapList{}.ToVal overlapList{}._SegId overlapList{}._related_candidates overlapList{}._relationships{}.RefLink overlapList{}._relationships{}.de9im overlapList{}._relationships{}.fraPosisjon overlapList{}._relationships{}.pass{} overlapList{}._relationships{}.tilPosisjon overlapList{}.fortau_RefLink overlapList{}.fortau_fraPosisjon overlapList{}.fortau_tilPosisjon overlapList{}.fraPosisjon overlapList{}.fylkeNr overlapList{}.hovedParsell overlapList{}.kode overlapList{}.kommuneNr overlapList{}.sideposisjon overlapList{}.tilPosisjon overlapList{}.vegkategori overlapList{}.veglenkeMeterFra overlapList{}.veglenkeMeterTil overlapList{}.vegnummer overlapList{}.vegstatus
    REMOVE_ATTRS = FromVal,OBJECTID,_related_candidates,_SegId,RoadLinkID,ToVal
    -> 4_Fortau_VedGSveg
    -> 4_Fortau_VedGSveg (writer XLSXW_1)
    -> 4_fortau_vedgsveg (writer SPATIALITE_1)
4_Fortau_VedGSveg: Inspector
4_Fortau_VedGSveg (writer XLSXW_1)
    attributes: NVDB_ID auto(20), vegkategori auto(20), vegnummer auto(20), vegstatus auto(20), hovedparsell auto(20), meterFra auto(20), meterTil auto(20), fylkeNr auto(20), kommuneNr auto(20), RefLink auto(20), fraPosisjon auto(20), tilPosisjon auto(20), sideposisjon auto(20), kode auto(20)
4_fortau_vedgsveg (writer SPATIALITE_1)
    attributes: nvdb_id string(200), vegkategori string(200), vegnummer string(200), vegstatus string(200), hovedparsell string(200), meterfra string(200), metertil string(200), fylkenr string(200), kommunenr string(200), reflink string(200), fraposisjon string(200), tilposisjon string(200), sideposisjon string(200), kode string(200)

Bookmark: Fortausobjekter fra API
Note: Henter objekter fra NVDB-API
HTTPCaller_2
    STATUS_CODE_ATTR = _http_status_code
    ERROR_ATTR = _error
    CUSTOM_HEADERS = Accept;application/vnd.vegvesen.nvdb-v1+xml
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/sok?kriterie={"lokasjon":{"kommune":["@Value(kommunenummer)"]},"objektTyper":[{"id":48,"antall":"100000","filter":[]}]}
    USE_COOKIES = No
    TARGET_ATTR_ENCODING = auto-detect
    TRANSFER_TIMEOUT_LENGTH = 90
    TARGET_ATTR = _url_contents
    -> XMLFeatureMapper_2
Note: Tolker XML
XMLFeatureMapper_2
    ATTRIBUTE_XML = _url_contents
    XML_SOURCE_NAME = _xml_source_
    MERGE_ATTRS = Yes
    FEATURE_COUNT_PER_XML = _xml_feature_count_
    SINGLE_XFMAP = $(xfmap_api)
    NEW_ATTRIBUTES = egengeometri geometriUtm33 vegreferanse{}.Vegreferanse.vegkategori vegreferanse{}.Vegreferanse.vegnummer vegreferanse{}.Vegreferanse.vegstatus vegreferanse{}.Vegreferanse.hovedParsell vegreferanse{}.Vegreferanse.veglenkeMeterFra vegreferanse{}.Vegreferanse.veglenkeMeterTil lineærPosisjon{}.lineærtObjektIdentifikasjon.Identifikasjon.lokalId lineærPosisjon{}.fraPosisjon lineærPosisjon{}.tilPosisjon lineærPosisjon{}.felt lineærPosisjon{}.sideposisjon vegreferanse{}.Vegreferanse.fylke vegreferanse{}.Vegreferanse.kommune NVDB_ID
    XML_INPUT_TYPE = Attribute with XML document
    FEATURE_TYPE_ATTR = fme_feature_type
    CONFIGURATION_TYPE = Single xfMap file
    MAPPED -> GeometryReplacer_2
Note: Tildeler geometri
GeometryReplacer_2
    REMOVE_ATTRIBUTE = Yes
    KIND_LONG = OGC Well Known Text
    SOURCE = @Value(geometriUtm33)
    OGC_WKT_PRECISION_DISPLAY = 64-bit
    -> CoordinateSystemSetter_2
CoordinateSystemSetter_2
    COORDSYS = $(coordsys)
    -> ListExploder_2
ListExploder_2
    ATTR_ACCUM_MODE = Merge Incoming List
    LIST_ATTR = lineærPosisjon{}
    INDEX_ATTR = _element_index
    ATTR_CONFLICT_RES = Use Incoming List
    ELEMENTS -> Fortau_API
    ELEMENTS -> ListExploder_3
Fortau_API: Inspector [off]
ListExploder_3
    ATTR_ACCUM_MODE = Merge Incoming List
    LIST_ATTR = vegreferanse{}
    INDEX_ATTR = _element_index
    ATTR_CONFLICT_RES = Use Incoming List
    ELEMENTS -> AttributeManager_6

Bookmark: Finner vegreferanse for start-posisjon på overlappstrekning
Note: Henter vegrerefranse fra NVDB-API
HTTPCaller_3
    STATUS_CODE_ATTR = _http_status_code
    ERROR_ATTR = _error
    CUSTOM_HEADERS = Accept;application/vnd.vegvesen.nvdb-v1+xml
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/vegreferanse/lenke?id=@Value(RefLink)&posisjon=@Value(FromVal)
    USE_COOKIES = No
    TARGET_ATTR_ENCODING = auto-detect
    TRANSFER_TIMEOUT_LENGTH = 90
    TARGET_ATTR = _url_contents
    -> XMLFlattener_2
XMLFlattener_2
    NEW_ATTRIBUTES = fylkeNr kommuneNr vegKategori vegStatus vegNummer hovedParsell meterVerdi
    FEATURE_TYPES_FORMAT_NAME = XML
    XML_SOURCE_TYPE = Attribute with XML document
    ATTRIBUTE_XML = _url_contents
    EMBEDDED_EXPRESSIONS = vegReferanseSok
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeManager_4

Bookmark: Fortausobjekter på lenker som har vegstatus G, U, H eller Q. Finner også hvilke temakoder som er brukt på veglenkene
Note: Finner overlappende kurvesegmenter
EventOverlayer_2
    FromVal = @Value(fraPosisjon)
    ToVal = @Value(tilPosisjon)
    RoadLinkID = @Value(RefLink)
    Common_Segments -> AttributeExposer_3
    Only_A -> AttributeExposer_3
AttributeExposer_3
    ATTR_LIST = NVDB_ID,kode
    -> FeatureMerger_2 [SUPPLIER]
Note: kobler segmentene til vegnett
FeatureMerger_2
    IGNORE_NULLS = No
    SUPPLIERS_FIRST = No
    LIST_NAME = overlapList
    MERGE_TYPE = Attributes Only
    JOIN_KEYS = @Value(NVDB_ID) @Value(NVDB_ID) AUTO
    REJECT_NULL_MISSING_KEYS = No
    ATTR_ACCUM_MODE = Merge Supplier
    ATTR_CONFLICT_RES = Use Requestor
    PROCESS_DUPS = No
    MERGED -> ListDuplicateRemover_2
ListDuplicateRemover_2
    SRC_LIST = overlapList{}.kode
    -> ListConcatenator_2
Note: Lager liste over temakoder
ListConcatenator_2
    SEP = ,
    VAL_ATTR = kode
    LIST_ATTR = overlapList{}.kode
    DROP_EMPTY_PARTS = No
    -> AttributeRemover_2
AttributeRemover_2
    LIST_ATTRS = overlapList{} overlapList{}.FromVal overlapList{}.OBJECTID overlapList{}.RefLink overlapList{}.RoadLinkID overlapList{}.ToVal overlapList{}._SegId overlapList{}.fraPosisjon overlapList{}.sideposisjon overlapList{}.tilPosisjon overlapList{}.vegreferanse{} overlapList{}.vegreferanse{}.fylke overlapList{}.vegreferanse{}.hovedParsell overlapList{}.vegreferanse{}.kommune overlapList{}.vegreferanse{}.vegkategori overlapList{}.vegreferanse{}.veglenkeMeterFra overlapList{}.vegreferanse{}.veglenkeMeterTil overlapList{}.vegreferanse{}.vegnummer overlapList{}.vegreferanse{}.vegstatus vegreferanse{} vegreferanse{}.fylke vegreferanse{}.hovedParsell vegreferanse{}.kommune vegreferanse{}.vegkategori vegreferanse{}.veglenkeMeterFra vegreferanse{}.veglenkeMeterTil vegreferanse{}.vegnummer vegreferanse{}.vegstatus
    REMOVE_ATTRS = FromVal,OBJECTID,_SegId,RoadLinkID,ToVal
    -> 3_Fortau_VegreferanseGS
    -> 3_Fortau_VegreferanseGS (writer XLSXW_1)
    -> 3_fortau_vegreferansegs (writer SPATIALITE_1)
3_Fortau_VegreferanseGS: Inspector
3_Fortau_VegreferanseGS (writer XLSXW_1)
    attributes: NVDB_ID auto(20), vegkategori auto(20), vegnummer auto(20), vegstatus auto(20), hovedparsell auto(20), meterFra auto(20), meterTil auto(20), fylkeNr auto(20), kommuneNr auto(20), RefLink auto(20), fraPosisjon auto(20), tilPosisjon auto(20), sideposisjon auto(20), kode auto(20)
3_fortau_vegreferansegs (writer SPATIALITE_1)
    attributes: nvdb_id string(200), vegkategori string(200), vegnummer string(200), vegstatus string(200), hovedparsell string(200), meterfra string(200), metertil string(200), fylkenr string(200), kommunenr string(200), reflink string(200), fraposisjon string(200), tilposisjon string(200), sideposisjon string(200), kode string(200)

Bookmark: Finner vegreferanse for start- og sluttposisjon på klippa vegreferansestrekning
CoordinateExtractor
    IND = 0
    MODE = Specify Coordinate
    X_ATTR = _x
    Y_ATTR = _y
    -> HTTPCaller_7
Note: Henter vegrerefranse fra NVDB-API
HTTPCaller_7
    STATUS_CODE_ATTR = _http_status_code
    ERROR_ATTR = _error
    CUSTOM_HEADERS = Accept;application/vnd.vegvesen.nvdb-v1+xml
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/vegreferanse/koordinat?ost=@Value(_x)&nord=@Value(_y)
    USE_COOKIES = No
    TARGET_ATTR_ENCODING = auto-detect
    TRANSFER_TIMEOUT_LENGTH = 90
    TARGET_ATTR = _url_contents
    -> XMLFlattener_4
XMLFlattener_4
    NEW_ATTRIBUTES = veglenkeId veglenkePosisjon
    FEATURE_TYPES_FORMAT_NAME = XML
    XML_SOURCE_TYPE = Attribute with XML document
    ATTRIBUTE_XML = _url_contents
    EMBEDDED_EXPRESSIONS = vegReferanseSok
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeManager_7
AttributeManager_7
    ATTR_TABLE:
      REMOVE _clipped
      REMOVE _headers{}.name
      REMOVE _headers{}.value
      REMOVE _url_contents
      REMOVE _http_status_code
      RENAME_SET_VALUE veglenkeId > RefLink
      RENAME_SET_VALUE veglenkePosisjon > fraPosisjon
      REMOVE _x
      REMOVE _y
    -> CoordinateExtractor_3
CoordinateExtractor_3
    IND = -1
    MODE = Specify Coordinate
    X_ATTR = _x
    Y_ATTR = _y
    -> HTTPCaller_6
Note: Henter vegrerefranse fra NVDB-API
HTTPCaller_6
    STATUS_CODE_ATTR = _http_status_code
    ERROR_ATTR = _error
    CUSTOM_HEADERS = Accept;application/vnd.vegvesen.nvdb-v1+xml
    CONNECTION_TIMEOUT_LENGTH = 60
    VERIFY_SSL_CERTIFICATES = Yes
    SAVE_FILE = Attribute
    HTTP_METHOD = GET
    FOLLOW_REDIRECTS = Yes
    RESPONSE_HEADER_LIST_ATTR = _headers
    TARGET_URL = https://www.vegvesen.no/nvdb/api/vegreferanse/koordinat?ost=@Value(_x)&nord=@Value(_y)
    USE_COOKIES = No
    TARGET_ATTR_ENCODING = auto-detect
    TRANSFER_TIMEOUT_LENGTH = 90
    TARGET_ATTR = _url_contents
    -> XMLFlattener_5
XMLFlattener_5
    NEW_ATTRIBUTES = veglenkeId veglenkePosisjon
    FEATURE_TYPES_FORMAT_NAME = XML
    XML_SOURCE_TYPE = Attribute with XML document
    ATTRIBUTE_XML = _url_contents
    EMBEDDED_EXPRESSIONS = vegReferanseSok
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeManager_10
AttributeManager_10
    ATTR_TABLE:
      REMOVE _headers{}.name
      REMOVE _headers{}.value
      REMOVE _url_contents
      REMOVE _http_status_code
      RENAME_SET_VALUE veglenkeId > RefLink
      RENAME_SET_VALUE veglenkePosisjon > tilPosisjon
      REMOVE _x
      REMOVE _y
    -> EventOverlayer_4 [Event_table_A]

FME custom transformer EventOverlayer

Parameters:
- RoadLinkID =   # " " RoadLinkID
- FromVal =   # " " FromVal
- ToVal =   # " " ToVal

Event_table_A (input)
    -> AttributeCreator_2
AttributeCreator_2
    ATTR_TABLE:
      SET_TO RoadLinkID = $(RoadLinkID)
      SET_TO FromVal = $(FromVal)
      SET_TO ToVal = $(ToVal)
    -> GeometryRemover
GeometryRemover
    -> SegmentizeTable [Events]
    -> Segments [Event_Tables]
Event_table_B (input)
    -> AttributeCreator_3
AttributeCreator_3
    ATTR_TABLE:
      SET_TO RoadLinkID = $(RoadLinkID)
      SET_TO FromVal = $(FromVal)
      SET_TO ToVal = $(ToVal)
    -> GeometryRemover_2
GeometryRemover_2
    -> Segments [Event_Tables]
    -> SegmentizeTable_2 [Events]
Note: Common segments
Segments
    FromVal = @Value(FromVal)
    __COMPOUND_PARAMETERS = -
    ToVal = @Value(ToVal)
    RoadLinkID = @Value(RoadLinkID)
    Unique_Segment_List -> SegmentizeTable [SegmentList]
    Unique_Segment_List -> SegmentizeTable_2 [SegmentList]
Note: Segmentize table A
SegmentizeTable
    eventToVal = @Value(ToVal)
    eventRoadLink = @Value(RoadLinkID)
    __COMPOUND_PARAMETERS = -
    eventFromVal = @Value(FromVal)
    Segmented -> FeatureMerger [REQUESTOR]
Note: Segmentize table B
SegmentizeTable_2
    eventToVal = @Value(ToVal)
    eventRoadLink = @Value(RoadLinkID)
    __COMPOUND_PARAMETERS = -
    eventFromVal = @Value(FromVal)
    Segmented -> FeatureMerger [SUPPLIER]
Note: Merge segments
FeatureMerger
    IGNORE_NULLS = No
    SUPPLIERS_FIRST = No
    MERGE_TYPE = Attributes Only
    JOIN_KEYS = @Value(_SegId) @Value(_SegId) AUTO
    REJECT_NULL_MISSING_KEYS = No
    ATTR_ACCUM_MODE = Merge Supplier
    ATTR_CONFLICT_RES = Use Requestor
    PROCESS_DUPS = No
    MERGED -> Common_Segments (output)
    NOT_MERGED -> Only_A (output)
    UNREFERENCED -> Only_B (output)
Common_Segments (output)
Only_A (output)
Only_B (output)

FME custom transformer SegmentizeTable
Splits an event table based on a list of segments with from-to-measure

Parameters:
- eventRoadLink =   # Event Table Road Link ID Attribute
- eventFromVal =   # Event Table from meassure
- eventToVal =   # Event Table To Meassure

Events (input)
    -> AttributeCreator
SegmentList (input)
    -> AttributeExposer
Note: Create common segments
InlineQuerier
    QUERY_DEF:
      EventSegments,Select * FROM Events
      INNER JOIN Segments ON Events.RoadLinkID = Segments.RoadLinkID
      WHERE (Segments.segFromVal < Events.eventToVal AND Segments.segToVal > Events.eventFromVal),FIRST
    QUERY_SCHEMA = EventSegments,RoadLinkID,varchar(30),eventFromVal,float,eventToVal,float,Events.fme_feature_content,fme_feature_content,segFromVal,float,segToVal,float,Segments.fme_feature_content,fme_feature_content
    TABLE_DEF = Events,RoadLinkID,varchar(30),eventFromVal,float,eventToVal,float,Segments,RoadLinkID,varchar(30),segFromVal,float,segToVal,float
    EventSegments -> AttributeManager
AttributeManager
    ATTR_TABLE:
      SET_TO FromVal = @Value(segFromVal)
      SET_TO ToVal = @Value(segToVal)
      REMOVE eventFromVal
      REMOVE eventToVal
      REMOVE segFromVal
      REMOVE segToVal
    -> Segmented (output)
Segmented (output)

Bookmark: Link ID and measure attributes
AttributeCreator
    ATTR_TABLE:
      SET_TO RoadLinkID = $(eventRoadLink)
      SET_TO eventFromVal = $(eventFromVal)
      SET_TO eventToVal = $(eventToVal)
    -> InlineQuerier [Events]
AttributeExposer
    ATTR_LIST = RoadLinkID,FromVal,ToVal
    -> AttributeExpressionRenamer
AttributeExpressionRenamer: BulkAttributeRenamer
    MODE_CHOICE = RENAME
    ATTRCHOICE = Selected Attributes
    ATTRLIST = FromVal ToVal
    PATTERN_ACTION_DISP = ADDPREFIX
    REPLACE_STR = seg
    -> InlineQuerier [Segments]

FME custom transformer UniqeSegments

BREAKPOINTLIST (input)
    -> AttributeExposer_3
AttributeExposer_3
    ATTR_LIST = _idx,_maxIdx,RoadLinkID,_Bp_list{}.BREAKPOINT,_Bp_list{}.RoadLinkID,_Bp_list{}.fme_feature_type,_Bp_list{}.fme_basename,_Bp_list{}.fme_dataset
    -> ListIndexer

Bookmark: From value
ListIndexer
    INDEX = @Value(_idx)
    LIST_ATTR = _Bp_list{}
    -> AttributeExposer
AttributeExposer
    ATTR_LIST = BREAKPOINT
    -> AttributeManager
AttributeManager
    ATTR_TABLE:
      RENAME_SET_VALUE BREAKPOINT > FromVal
      SET_TO _next = @Evaluate(@Value(_idx)+1)
    -> ListIndexer_2

Bookmark: To value
ListIndexer_2
    INDEX = @Value(_next)
    LIST_ATTR = _Bp_list{}
    -> AttributeExposer_2
AttributeExposer_2
    ATTR_LIST = BREAKPOINT
    -> AttributeManager_2
AttributeManager_2
    ATTR_TABLE:
      RENAME_SET_VALUE BREAKPOINT > ToVal
      SET_TO _next = @Evaluate(@Value(_idx)+1)
    -> AttributeManager_3
    -> TestFilter

Bookmark: Finished segements
AttributeManager_3
    ATTR_TABLE:
      REMOVE _idx
      REMOVE _maxIdx
      REMOVE _next
      REMOVE _Bp_list{}.BREAKPOINT
      REMOVE _Bp_list{}.RoadLinkID
      REMOVE _Bp_list{}.fme_feature_type
      REMOVE _Bp_list{}.fme_basename
      REMOVE _Bp_list{}.fme_dataset
    -> Unique_Segments (output)
Unique_Segments (output)

Bookmark: Test for more segments
TestFilter
    TEST_LIST = BOOL_OP,OR,COMPOSITE_TEST,<Unused>,TEST_CLAUSE,"TEST @Value(_next) = @Value(_maxIdx)",Last
    DEFAULT_VALUE = <UNFILTERED>
    <UNFILTERED> -> AttributeCreator
AttributeCreator
    ATTR_TABLE = SET_TO _idx = @Value(_next)
    -> BREAKPOINTLIST (output)
BREAKPOINTLIST (output)

FME custom transformer Segments
Creates a list of segments with RoladLinkID, from meassure and to-meassure from an overlay between event tables

Parameters:
- RoadLinkID =   # " " RoadLinkID
- FromVal =   # " " FromVal
- ToVal =   # " " ToVal

Event_Tables (input)
    -> AttributeCreator_2
Note: Loop for creating unique table of segments
UniqeSegments
    __COMPOUND_PARAMETERS = -
    Unique_Segments -> AttributeManager
AttributeManager
    ATTR_TABLE = SET_TO _SegId = @Value(RoadLinkID)_@Value(FromVal)_@Value(ToVal)
    -> Unique_Segment_List (output)
Unique_Segment_List (output)

Bookmark: Link ID and meassure attributes
AttributeCreator_2
    ATTR_TABLE:
      SET_TO RoadLinkID = $(RoadLinkID)
      SET_TO FromVal = $(FromVal)
      SET_TO ToVal = $(ToVal)
    -> AttributeKeeper
AttributeKeeper
    KEEP_ATTRS = RoadLinkID,FromVal,ToVal
    -> ATTRIBUTERENAMER_3
    -> ATTRIBUTERENAMER_4

Bookmark: Create a list of all unique breakpoints pr RoadLinkID
Note: From
ATTRIBUTERENAMER_3: AttributeRenamer
    ATTR_TABLE = RENAME_SET_DEFAULT FromVal > BREAKPOINT
    -> AttributeKeeper_2
Note: To
ATTRIBUTERENAMER_4: AttributeRenamer
    ATTR_TABLE = RENAME_SET_DEFAULT ToVal > BREAKPOINT
    -> AttributeKeeper_2
AttributeKeeper_2
    KEEP_ATTRS = RoadLinkID,BREAKPOINT
    -> DuplicateFilter
DuplicateFilter
    INPUT_ORDERED_CHOICE = No
    KEYATTR = RoadLinkID BREAKPOINT
    UNIQUE -> ListBuilder
ListBuilder
    LIST_NAME = _Bp_list
    GRP_BY = RoadLinkID
    -> ListSorter
ListSorter
    TYPE = Numeric
    SRC_LIST = _Bp_list{}.BREAKPOINT
    ORDER = Ascending
    -> ListElementCounter
ListElementCounter
    LIST_NAME = _Bp_list{}
    CNT_ATTR = _element_count
    -> AttributeManager_2
AttributeManager_2
    ATTR_TABLE:
      SET_TO _maxIdx = @Evaluate(@Evaluate(@Value(_element_count)-1))
      REMOVE _element_count
      SET_TO _idx = 0
    -> UniqeSegments [BREAKPOINTLIST]
