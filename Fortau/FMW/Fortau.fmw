FME workspace Fortau.fmw

Parameters:
- omr = fylke   # Områdetype
- NUM = 1   # Number to Create
- START = 1   # Første nummer
- dataFolder = C:\DATA\GitHub\VegnettKvalitet\Fortau\Data   # Mappe med resultatfiler
- today:   # Python Script
      import time
      ## dd/mm/yyyy format
      time.strftime("%Y%m%d")

Writers:
- XLSXW_1: XLSXW to $(dataFolder)\$(today)\Fortau.xls
- SPATIALITE_1: SPATIALITE to $(dataFolder)\$(today)\Fortau.db in EPSG:25833
- TEXTLINE_1: TEXTLINE to $(dataFolder)\$(today)

Fortau_Vegnett: Inspector
AttributeManager
    ATTR_TABLE:
      REMOVE startnode
      REMOVE sluttnode
      RENAME_SET_VALUE veglenkeid > route_id
      RENAME_SET_VALUE startposisjon > from_measure
      RENAME_SET_VALUE sluttposisjon > to_measure
    -> InlineQuerier [Veglenker]
    -> AttributeManager_3
AttributeManager_3
    ATTR_TABLE:
      REMOVE typeVeg
      REMOVE id
      REMOVE geometri.wkt
      RENAME_SET_VALUE from_measure > fraposisjon
      RENAME_SET_VALUE to_measure > tilposisjon
      RENAME_SET_VALUE route_id > reflink
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE epsg
      REMOVE detaljnivå
      REMOVE datafangstdato
      REMOVE medium
      REMOVE kvalitet.Posisjonskvalitet.synbarhet
      REMOVE temakode
      SET_TO _feil = Veglenke med temakode Fortau (7046)
      SET_TO fme_feature_type = 1_VegnettFortau
    -> 1_VegnettFortau
    -> AttributeManager_3_OUTPUT
1_VegnettFortau: Inspector
Note: Resultatfiler
AttributeManager_3_OUTPUT: Junction
    -> Counter_3
Note: 1_vegnettfortau
Counter_3: Junction
    -> Counter
AttributeExposer
    ATTR_LIST = vegreferanse{}.Vegreferanse.fylke,vegreferanse{}.Vegreferanse.kommune,vegreferanse{}.Vegreferanse.vegkategori,vegreferanse{}.Vegreferanse.vegstatus,vegreferanse{}.Vegreferanse.hovedparsell,vegreferanse{}.Vegreferanse.vegnummer,vegreferanse{}.Vegreferanse.veglenkeMeterFra,vegreferanse{}.Vegreferanse.veglenkeMeterTil,lineærPosisjon{}.LineærPosisjonStrekning.nettverkselement.id,lineærPosisjon{}.LineærPosisjonStrekning.fraPosisjon,lineærPosisjon{}.LineærPosisjonStrekning.tilPosisjon,lineærPosisjon{}.LineærPosisjonStrekning.sideposisjon
    -> ListExploder
    -> ListExploder_2
ListExploder_2
    LIST_ATTR = lineærPosisjon{}
    INDEX_ATTR = _element_index
    ATTR_ACCUM_MODE = Merge Incoming List
    ATTR_CONFLICT_RES = Use Incoming List
    ELEMENTS -> AttributeManager_2
AttributeManager_2
    ATTR_TABLE:
      REMOVE lokasjon.stedfestinger.stedfesting.veglenkeid
      REMOVE lokasjon.stedfestinger.stedfesting.fra_posisjon
      REMOVE lokasjon.stedfestinger.stedfesting.til_posisjon
      RENAME_SET_VALUE LineærPosisjonStrekning.nettverkselement.id > route_id
      RENAME_SET_VALUE LineærPosisjonStrekning.fraPosisjon > from_measure
      RENAME_SET_VALUE LineærPosisjonStrekning.tilPosisjon > to_measure
      RENAME_SET_VALUE LineærPosisjonStrekning.sideposisjon > sideposisjon
    -> InlineQuerier [Fortau]
Note: Finner veglenke med type fortau, der stedfesting overlapper fortausobjekter
InlineQuerier
    TABLE_DEF = Veglenker,typeVeg,varchar(200),id,varchar(200),geometri.wkt,varchar(200),from_measure,varchar(200),to_measure,varchar(200),route_id,varchar(200),xml_fragment,varchar(200),xml_id,varchar(200),xml_matched_element,varchar(200),xml_parent_id,varchar(200),xml_parent_child_pos,varchar(200),fme_feature_type,varchar(200),identifikasjon.Identifikasjon.lokalId,varchar(200),identifikasjon.Identifikasjon.versjonId,varchar(200),identifikasjon.Identifikasjon.navnerom,varchar(200),gml_id,varchar(200),epsg,varchar(200),detaljnivå,varchar(200),startposisjon,varchar(200),sluttposisjon,varchar(200),datafangstdato,varchar(200),medium,varchar(200),kvalitet.Posisjonskvalitet.synbarhet,varchar(200),temakode,varchar(200),Fortau,id,varchar(200),geometri.wkt,varchar(200),xml_fragment,varchar(200),xml_id,varchar(200),xml_matched_element,varchar(200),xml_parent_id,varchar(200),xml_parent_child_pos,varchar(200),fme_feature_type,varchar(200),identifikasjon.Identifikasjon.lokalId,varchar(200),identifikasjon.Identifikasjon.versjonId,varchar(200),identifikasjon.Identifikasjon.navnerom,varchar(200),gml_id,varchar(200),assosiasjoner{}.typeId,varchar(200),assosiasjoner{}.vegobjektId,varchar(200),assosiasjoner{}.relasjonstype,varchar(200),epsg,varchar(200),route_id,varchar(200),from_measure,varchar(200),to_measure,varchar(200),_hierarchy_child_id_list{},varchar(200),_geometry_name,varchar(200),_hierarchy_id,varchar(200),_hierarchy_parent_id,varchar(200),_part_number,varchar(200)
    QUERY_DEF:
      Overlapp,SELECT * FROM Veglenker
      LEFT JOIN Fortau ON Veglenker.route_id = Fortau.route_id
      WHERE (Veglenker.from_measure < Fortau.to_measure AND Veglenker.to_measure > Fortau.from_measure)
      ,FIRST
    QUERY_SCHEMA = Overlapp,typeVeg,varchar(200),id,varchar(200),geometri.wkt,varchar(200),from_measure,varchar(200),to_measure,varchar(200),route_id,varchar(200),xml_fragment,varchar(200),xml_id,varchar(200),xml_matched_element,varchar(200),xml_parent_id,varchar(200),xml_parent_child_pos,varchar(200),fme_feature_type,varchar(200),identifikasjon.Identifikasjon.lokalId,varchar(200),identifikasjon.Identifikasjon.versjonId,varchar(200),identifikasjon.Identifikasjon.navnerom,varchar(200),gml_id,varchar(200),epsg,varchar(200),detaljnivå,varchar(200),startposisjon,varchar(200),sluttposisjon,varchar(200),datafangstdato,varchar(200),medium,varchar(200),kvalitet.Posisjonskvalitet.synbarhet,varchar(200),temakode,varchar(200),Veglenker.fme_feature_content,fme_feature_content,assosiasjoner{}.typeId,varchar(200),assosiasjoner{}.vegobjektId,varchar(200),assosiasjoner{}.relasjonstype,varchar(200),_hierarchy_child_id_list{},varchar(200),_geometry_name,varchar(200),_hierarchy_id,varchar(200),_hierarchy_parent_id,varchar(200),_part_number,varchar(200),Fortau.fme_feature_content,fme_feature_content
    Overlapp -> AttributeManager_5
AttributeManager_5
    ATTR_TABLE:
      REMOVE typeVeg
      REMOVE id
      REMOVE geometri.wkt
      RENAME_SET_VALUE from_measure > fraposisjon
      RENAME_SET_VALUE to_measure > tilposisjon
      RENAME_SET_VALUE route_id > reflink
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE epsg
      REMOVE detaljnivå
      REMOVE datafangstdato
      REMOVE medium
      REMOVE kvalitet.Posisjonskvalitet.synbarhet
      REMOVE temakode
      SET_TO _feil = Overlapp fortau som objekt og som veglenke
      SET_TO fme_feature_type = 2_Dobbelfortau
      REMOVE startposisjon
      REMOVE sluttposisjon
      REMOVE assosiasjoner{}.typeId
      REMOVE assosiasjoner{}.vegobjektId
      REMOVE assosiasjoner{}.relasjonstype
      REMOVE _hierarchy_child_id_list{}
      REMOVE _geometry_name
      REMOVE _hierarchy_id
      REMOVE _hierarchy_parent_id
      REMOVE _part_number
    -> AttributeManager_5_OUTPUT
    -> 2_Dobbelfortau
Note: Resultatfiler
AttributeManager_5_OUTPUT: Junction
    -> Counter_4
Note: 2_dobbelfortau
Counter_4: Junction
    -> Counter
2_Dobbelfortau: Inspector
ListExploder
    LIST_ATTR = vegreferanse{}
    INDEX_ATTR = _element_index
    ATTR_ACCUM_MODE = Merge Incoming List
    ATTR_CONFLICT_RES = Use Incoming List
    ELEMENTS -> TestFilter_2
Note: Fortau på vegreferanse G, U, H eller Q
TestFilter_2
    DEFAULT_VALUE = <UNFILTERED>
    TEST_LIST = BOOL_OP,OR,COMPOSITE_TEST,<Unused>,TEST_CLAUSE,"TEST @Value(Vegreferanse.vegstatus) IN G, U, H, Q",GS-veg
    GS-veg -> AttributeManager_6
    <UNFILTERED> -> GeometryExtractor
AttributeManager_6
    ATTR_TABLE:
      REMOVE id
      REMOVE geometri.wkt
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE epsg
      SET_TO _feil = Fortau på vegreferanse GS-veg (@Value(Vegreferanse.vegkategori)@Value(Vegreferanse.vegstatus)@Value(Vegreferanse.vegnummer))
      SET_TO fme_feature_type = 3_FortauMedVRefGS
      REMOVE assosiasjoner{}.typeId
      REMOVE assosiasjoner{}.vegobjektId
      REMOVE assosiasjoner{}.relasjonstype
      REMOVE _hierarchy_child_id_list{}
      REMOVE _geometry_name
      REMOVE _hierarchy_id
      REMOVE _hierarchy_parent_id
      REMOVE _part_number
      REMOVE lokasjon.stedfestinger.stedfesting.veglenkeid
      REMOVE lokasjon.stedfestinger.stedfesting.fra_posisjon
      REMOVE lokasjon.stedfestinger.stedfesting.til_posisjon
      REMOVE Vegreferanse.vegkategori
      REMOVE Vegreferanse.vegstatus
      REMOVE Vegreferanse.hovedparsell
      REMOVE Vegreferanse.vegnummer
      REMOVE Vegreferanse.veglenkeMeterFra
      REMOVE Vegreferanse.veglenkeMeterTil
      REMOVE lineærPosisjon{}.LineærPosisjonStrekning.nettverkselement.id
      REMOVE lineærPosisjon{}.LineærPosisjonStrekning.fraPosisjon
      REMOVE lineærPosisjon{}.LineærPosisjonStrekning.tilPosisjon
      REMOVE lineærPosisjon{}.LineærPosisjonStrekning.sideposisjon
      REMOVE _element_index
    -> 3_FortauMedVRefGS
    -> Matcher
3_FortauMedVRefGS: Inspector
Matcher
    MATCH = 2D
    BLANK_AND_MISSING_DIFFER = No
    LENIENT_MATCH = No
    CNT_ATTR = _match_id
    MATCHATTRS = Vegreferanse.fylke _feil Vegreferanse.kommune fme_feature_type
    MATCH_STRATEGY = Match Selected Attributes
    SINGLE_MATCHED -> AttributeManager_6_OUTPUT
    NOT_MATCHED -> AttributeManager_6_OUTPUT
Note: Resultatfiler
AttributeManager_6_OUTPUT: Junction
    -> Counter_5
Note: 3_fortau_vegreferansegs
Counter_5: Junction
    -> Counter
GeometryExtractor
    OGCVERSION = 1.1
    LEVELS_ATTR = _levels
    MSSQL_FORMAT_CHOICE = Geometry
    ELLIPSOID_NAME = WGS84
    PREFER_POLYGON_OVER_SURFACE = No
    ATTR = _geometry
    PRECISION = 0
    OMIT_NAMESPACES_DISPLAY = No
    LETTERING = WGS84
    OGEOSMS_URL_PREFIX = http://maps.google.com/?q=
    OGC_WKT_PRECISION_DISPLAY = Shortened 64-bit
    GEOHASH_PRECISION_DISPLAY = ~9.3 mm (12 characters)
    KIND_LONG = FME Binary
    REMOVE_GEOMETRY = No
    -> LengthCalculator
LengthCalculator
    LEN_ATTR = _fortaulengde
    MULT = 1
    DIM = 2
    -> Bufferer
Note: Bufferer [Bufferer:11] / Group By: <not set> / Buffer Amount: 10 / End Cap Style: Square / Stroking Density: 8 / List Name: <not set> / Version: 11 / Last Parameter Edit: Build 16481
Bufferer
    CAP_STYLE = Square
    OFFSET = 10
    INTERP_SEGMENTS = 8
    BUFFERED -> Counter_6
Counter_6
    DOMAIN = counter
    SCOPE = Global
    CNT_ATTR = _bufferId
    START = 0
    -> Counter_6_OUTPUT_-__Clipper_CLIPPER
Counter_6_OUTPUT_-__Clipper_CLIPPER: Junction
    -> Clipper [CLIPPER]
    -> GeometryReplacer
GeometryReplacer
    REMOVE_ATTRIBUTE = Yes
    SOURCE = @Value(_geometry)
    KIND_LONG = FME Binary
    -> FeatureMerger [REQUESTOR]
Fortausobjekter: Inspector
AttributeExposer_3
    ATTR_LIST = vegstatus
    -> AttributeManager_7
AttributeManager_7
    ATTR_TABLE:
      REMOVE id
      REMOVE geometri.wkt
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE assosiasjoner{}.typeId
      REMOVE assosiasjoner{}.vegobjektId
      REMOVE assosiasjoner{}.relasjonstype
      REMOVE epsg
      REMOVE lokasjon.stedfestinger.stedfesting.veglenkeid
      REMOVE lokasjon.stedfestinger.stedfesting.fra_posisjon
      REMOVE lokasjon.stedfestinger.stedfesting.til_posisjon
      REMOVE _hierarchy_child_id_list{}
      REMOVE _geometry_name
      REMOVE _hierarchy_id
      REMOVE _hierarchy_parent_id
      REMOVE _part_number
      REMOVE _schemamapper_row_ids
    -> Clipper [CLIPPEE]
Note: Avgrenser vegreferanselenkene til buffer
Clipper
    CREATE_AGGREGATES = Yes
    BOUNDARY_CASES = Treat as Inside
    CLIP_TYPE = Multiple Clippers
    LINES_AS_SEGMENTS = No
    CONNECT_Z_MODE = First Wins
    ATTR_ACCUM_MODE = Merge Clipper
    PRESERVE_CLIPPEE_EXTENTS = No
    ATTR_CONFLICT_RES = Use Clipper
    CLIPPED_ATTR = _clipped
    INSIDE -> LengthCalculator_2
LengthCalculator_2
    LEN_ATTR = _vreflengde
    MULT = 1
    DIM = 2
    -> Aggregator_2
Aggregator_2
    AGGREGATE_TYPE = Homogeneous Collection (If Possible)
    ACCUM_ATTRS_NAME = Get Attributes From One Representative Feature
    SUM = _vreflengde
    SEP = ,
    ORDERED = No
    MODE = Geometry - Assemble One Level
    GROUP_BY = vegstatus _bufferId
    AGGREGATE -> Aggregator
Aggregator
    CONCAT_ATTRS = vegstatus
    AGGREGATE_TYPE = Homogeneous Collection (If Possible)
    ACCUM_ATTRS_NAME = Get Attributes From One Representative Feature
    SUM = _vreflengde
    SEP = ,
    ORDERED = No
    MODE = Geometry - Assemble One Level
    GROUP_BY = _bufferId
    AGGREGATE -> TestFilter_3
TestFilter_3
    DEFAULT_VALUE = <UNFILTERED>
    TEST_LIST = BOOL_OP,OR,COMPOSITE_TEST,<Unused>,TEST_CLAUSE,"TEST @Evaluate(@Value(_vreflengde)/@Value(_fortaulengde)) > 0.3",30pst
    30pst -> FeatureMerger [SUPPLIER]
Note: Kobler fortau og vegreferanselenker
FeatureMerger
    MERGE_TYPE = Attributes Only
    IGNORE_NULLS = No
    CONNECT_Z_MODE = First Wins
    SUPPLIERS_FIRST = No
    GEOM_TYPE = Build Polygons
    REJECT_NULL_MISSING_KEYS = No
    JOIN_KEYS = @Value(_bufferId) @Value(_bufferId) AUTO
    ATTR_ACCUM_MODE = Merge Supplier
    ATTR_CONFLICT_RES = Use Requestor
    PROCESS_DUPS = Yes
    MERGED -> AttributeManager_8
AttributeManager_8
    ATTR_TABLE:
      REMOVE id
      REMOVE geometri.wkt
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE epsg
      SET_TO _feil = Fortau med nærliggende vegreferanse GS-veg (@Value(vegstatus))
      SET_TO fme_feature_type = 4_FortauVedVRefGS
      REMOVE assosiasjoner{}.typeId
      REMOVE assosiasjoner{}.vegobjektId
      REMOVE assosiasjoner{}.relasjonstype
      REMOVE _hierarchy_child_id_list{}
      REMOVE _geometry_name
      REMOVE _hierarchy_id
      REMOVE _hierarchy_parent_id
      REMOVE _part_number
      REMOVE lokasjon.stedfestinger.stedfesting.veglenkeid
      REMOVE lokasjon.stedfestinger.stedfesting.fra_posisjon
      REMOVE lokasjon.stedfestinger.stedfesting.til_posisjon
      REMOVE Vegreferanse.fylke
      REMOVE Vegreferanse.kommune
      REMOVE Vegreferanse.vegkategori
      REMOVE Vegreferanse.vegstatus
      REMOVE Vegreferanse.hovedparsell
      REMOVE Vegreferanse.vegnummer
      REMOVE Vegreferanse.veglenkeMeterFra
      REMOVE Vegreferanse.veglenkeMeterTil
      REMOVE lineærPosisjon{}.LineærPosisjonStrekning.nettverkselement.id
      REMOVE lineærPosisjon{}.LineærPosisjonStrekning.fraPosisjon
      REMOVE lineærPosisjon{}.LineærPosisjonStrekning.tilPosisjon
      REMOVE lineærPosisjon{}.LineærPosisjonStrekning.sideposisjon
      REMOVE _element_index
      REMOVE _bufferId
      REMOVE _geometry
      REMOVE _clipped
    -> 4_FortauVedVRefGS
    -> AttributeManager_8_OUTPUT
Note: Resulatfiler
AttributeManager_8_OUTPUT: Junction
    -> Counter_7
Note: 4_FortauVedVRefGS
Counter_7: Junction
    -> Counter
Counter
    DOMAIN = counter
    SCOPE = Global
    CNT_ATTR = NVDB_ID
    START = 0
    -> CenterPointReplacer
    -> NeighborFinder_5 [CANDIDATE]
Sorter
    SORT_PARM = _feil ALPHA ASCENDING kortform ALPHA ASCENDING
    SORTED -> StringConcatenator_2
StringConcatenator_2
    PARM_LINE = FEIL: @Value(_y) @Value(_x) @Value(_feil), vegreferanse @Value(kortform)
    VAL_ATTR = text_line_data
    ACTION = Create New Attribute
    -> text_line (writer TEXTLINE_1)
    -> 1_vegnettfortau (writer SPATIALITE_1)
    -> 1_vegnettfortau (writer XLSXW_1)
Note: Fylkesvise GL Feilfiler
text_line (writer TEXTLINE_1)
    attributes: text_line_data buffer
1_vegnettfortau (writer SPATIALITE_1)
    attributes: fylke integer, kommune integer, vegkategori string(200), vegstatus string(200), vegnummer integer, hp integer, meter integer, kortform string(200), feil string(20)
1_vegnettfortau (writer XLSXW_1)
    attributes: fylke number(20), kommune number(20), vegkategori number(20), vegstatus string(20), vegnummer number(20), hp number(20), meter number(20), kortform string(20), feil string(20)
4_FortauVedVRefGS: Inspector
Vegreferanse: Inspector

Bookmark: Utvalg (antall fylker og nummer)
Creator_2
    NUM = $(NUM)
    GEOMTYPE = Geometry Object
    CREATED -> Counter_2
Counter_2
    DOMAIN = counter
    SCOPE = Local
    CNT_ATTR = omrNvn
    START = $(START)
    -> AttributeCreator
    -> AttributeCreator_2
    -> AttributeCreator_5

Bookmark: Temakode fortau i vegnett
Note: AttributeCreator_2 [AttributeCreator:8] / Substitute Missing, Null and Empty by: No Substitution / Set 'href' to 'https://www.utv.vegvesen.no/nvdb/api/v2/vegnett/lenker?$(omr)=@Value(omrNvn)&antall=5000' / Version: 8 / Last Parameter Edit: Build 16481
AttributeCreator_2
    ATTR_TABLE = SET_TO href = https://www.utv.vegvesen.no/nvdb/api/v2/vegnett/lenker?$(omr)=@Value(omrNvn)&antall=5000
    -> NVDB_Vegnettleser [_Input]
NVDB_Vegnettleser: NVDB_Vegnettleser_Enkel
    OMR = $(omr)
    namespace = vegvesen.no.nvdb
    OMRNVN = @Value(omrNvn)
    NESTE.HREF = @Value(href)
    nettverk:
      ns = FME_MacroValues['namespace'] + '.nw.' + FME_MacroValues['OMR'] + '_' + FME_MacroValues['OMRNVN']
      return ns
    Veglenke -> TestFilter
TestFilter
    DEFAULT_VALUE = <UNFILTERED>
    TEST_LIST = BOOL_OP,OR,COMPOSITE_TEST,<Unused>,TEST_CLAUSE,"TEST @Value(temakode) = 7046",Fortau
    Fortau -> Fortau_Vegnett
    Fortau -> AttributeManager

Bookmark: Fortausobjekter
Note: AttributeCreator [AttributeCreator:8] / Substitute Missing, Null and Empty by: No Substitution / Set 'href' to 'https://www.vegvesen.no/nvdb/api/v2/vegobjekter/48?$(omr)=@Value(omrNvn)&antall=5000&inkluder=alle' / Version: 8 / Last Parameter Edit: Build 16481
AttributeCreator
    ATTR_TABLE = SET_TO href = https://www.vegvesen.no/nvdb/api/v2/vegobjekter/48?$(omr)=@Value(omrNvn)&antall=5000&inkluder=alle
    -> NVDB_Leser [_Input]
Note: Fortausobjekter
NVDB_Leser
    NESTE.HREF = @Value(href)
    -> Fortausobjekter
    -> AttributeExposer

Bookmark: Leser vegreferanseobjekter med status G, U, H eller Q
Note: AttributeCreator_5 [AttributeCreator:8] / Substitute Missing, Null and Empty by: No Substitution / Set 'href' to 'https://www.vegvesen.no/nvdb/api/v2/vegobjekter/532?$(omr)=@Value(omrNvn)&egenskap="4567=12159 OR 4567=12160 OR 4567=12983 OR 4567=12986"&antall=5000&inkluder=alle' / Version: 8 / Last Parameter Edit: Build 16481
AttributeCreator_5
    ATTR_TABLE = SET_TO href = https://www.vegvesen.no/nvdb/api/v2/vegobjekter/532?$(omr)=@Value(omrNvn)&egenskap="4567=12159 OR 4567=12160 OR  4567=12983 OR  4567=12986"&antall=5000&inkluder=alle
    -> NVDB_Leser_3 [_Input]
Note: Vegreferranseobjekter
NVDB_Leser_3
    NESTE.HREF = @Value(href)
    -> SchemaMapper

Bookmark: Oversetter til GML-verdier og -navn
Note: Oversetter tillatte verdier til GML-verdier
SchemaMapper
    IDXDESTCOL = ""
    CSV__DUPLICATE_DELIMS = no
    CSV__SKIP_LINES = 1
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    FORMAT = CSV
    CSV_SCAN_MAX_FEATURES = 1000
    IDXSOURCECOL = ""
    CSV__SCHEMA = number,6,0,number,6,0,char,29,,char,34,
    IDXSOURCEATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    TABLE = CSV
    CSV__FIELD_NAMES_AFTER_HEADER = no
    ROW_ID_ATTR = _schemamapper_row_ids
    DATASET = https://raw.githubusercontent.com/jetgeo/NVDBGML/master/XSD/NVDB_enMapping.csv
    CSV__SCHEMA_WITH_COL_NAMES = ptid,number,6,0,enid,number,6,0,name,char,29,,fullname,char,34,
    MAP_ATTRS = enid ptid name
    IDXDESTATTR = fme_feature_type
    CSV__IN_SEPARATOR = ;
    CSV__SKIP_FOOTER = 0
    CSV__STRIP_QUOTES = yes
    CSV__IN_FIELD_NAMES = YES
    CSV__ALLOW_SPACES_IN_COLUMN_NAMES = yes
    CSV__GROUP_BY_DATASET = no
    MATCH_ATTRS = ptid enid
    MAPPED -> SchemaMapper_2
    UNMAPPED -> SchemaMapper_2
Note: Oversetter egenskapsnavn til GML-navn
SchemaMapper_2
    IDXDESTCOL = ""
    CSV__DUPLICATE_DELIMS = no
    CSV__SKIP_LINES = 1
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    FORMAT = CSV
    CSV_SCAN_MAX_FEATURES = 1000
    IDXSOURCECOL = ""
    CSV__SCHEMA = char,17,,number,3,0,number,6,0,char,22,
    IDXSOURCEATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    TABLE = CSV
    CSV__FIELD_NAMES_AFTER_HEADER = no
    ROW_ID_ATTR = _schemamapper_row_ids
    DATASET = https://raw.githubusercontent.com/jetgeo/NVDBGML/master/XSD/NVDB_ptMapping.csv
    CSV__SCHEMA_WITH_COL_NAMES = ft_attr,char,17,,ftid,number,3,0,ptid,number,6,0,name,char,22,
    MAP_ATTRS = ptid name """"""
    IDXDESTATTR = fme_feature_type
    CSV__IN_SEPARATOR = ;
    CSV__SKIP_FOOTER = 0
    CSV__STRIP_QUOTES = yes
    CSV__IN_FIELD_NAMES = YES
    CSV__ALLOW_SPACES_IN_COLUMN_NAMES = yes
    CSV__GROUP_BY_DATASET = no
    MATCH_ATTRS = ft_attr ftid
    MAPPED -> NullAttributeMapper_3
    UNMAPPED -> NullAttributeMapper_3
NullAttributeMapper_3
    NULL_TREATMENT = Missing
    SOURCE_ATTR_VAL = Empty Null
    ATTRCHOICE = All Attributes
    -> SchemaMapper_3
Note: Oversetter objekttypenavn til GML-navn
SchemaMapper_3
    IDXDESTCOL = name
    CSV__DUPLICATE_DELIMS = no
    CSV__SKIP_LINES = 1
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    FORMAT = CSV
    CSV_SCAN_MAX_FEATURES = 1000
    IDXSOURCECOL = ftid
    CSV__SCHEMA = number,3,0,char,18,
    IDXSOURCEATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    TABLE = CSV
    CSV__FIELD_NAMES_AFTER_HEADER = no
    ROW_ID_ATTR = _schemamapper_row_ids
    DATASET = https://raw.githubusercontent.com/jetgeo/NVDBGML/master/XSD/NVDB_ftMapping.csv
    CSV__SCHEMA_WITH_COL_NAMES = ftid,number,3,0,name,char,18,
    IDXDESTATTR = fme_feature_type
    CSV__IN_SEPARATOR = ;
    CSV__SKIP_FOOTER = 0
    CSV__STRIP_QUOTES = yes
    CSV__IN_FIELD_NAMES = YES
    CSV__ALLOW_SPACES_IN_COLUMN_NAMES = yes
    CSV__GROUP_BY_DATASET = no
    MAPPED -> AttributeExposer_3
    MAPPED -> Vegreferanse

Bookmark: Erstatter linjegeometri med punkt på linja
CenterPointReplacer
    CENTERPOINT -> NeighborFinder_5 [BASE]
NeighborFinder_5
    INSERT_VERTEX = No
    CANDIDATES_FIRST = No
    GROUP_BY = NVDB_ID
    MAX = 10000
    TREAT_POLYGON_AS = Lines
    MATCHED -> 2DPointReplacer
2DPointReplacer
    YVALATTR = @Value(_closest_candidate_y)
    XVALATTR = @Value(_closest_candidate_x)
    POINT -> CoordinateExtractor
CoordinateExtractor
    IND = 0
    X_ATTR = _x
    Z_DEFAULT = 0
    MODE = Specify Coordinate
    Y_ATTR = _y
    Z_ATTR = _z
    -> AttributeCreator_3
AttributeCreator_3
    ATTR_TABLE = SET_TO httpReq = https://www.vegvesen.no/nvdb/api/v2/posisjon.xml?nord=@Value(_y)&ost=@Value(_x)
    -> HTTPCaller_2
Note: Finner vegreferanse for representasjonspunktet
HTTPCaller_2
    STATUS_CODE_ATTR = _http_status_code
    TARGET_ATTR = _response_body
    SAVE_FILE = Attribute
    VERIFY_SSL_CERTIFICATES = Yes
    ERROR_ATTR = _error
    TARGET_URL = @Value(httpReq)
    RESPONSE_HEADER_LIST_ATTR = _headers
    HTTP_METHOD = GET
    USE_COOKIES = No
    TRANSFER_TIMEOUT_LENGTH = 90
    TARGET_ATTR_ENCODING = auto-detect
    FOLLOW_REDIRECTS = Yes
    CONNECTION_TIMEOUT_LENGTH = 60
    -> XMLFlattener_3
XMLFlattener_3
    NEW_ATTRIBUTES = fylke kommune kategori status nummer hp meter vegreferanse.kortform
    ATTRIBUTE_XML = _response_body
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = vegreferanse
    XML_SOURCE_TYPE = Attribute with XML document
    -> AttributeManager_4
AttributeManager_4
    ATTR_TABLE:
      RENAME_SET_VALUE kategori > vegkategori
      RENAME_SET_VALUE status > vegstatus
      RENAME_SET_VALUE nummer > vegnummer
      RENAME_SET_VALUE vegreferanse.kortform > kortform
      SET_TO feil = @Value(_feil)
    -> Sorter

FME custom transformer NVDB_Vegnettleser_Enkel
Leser og tolker data fra NVDB-API

Parameters:
- NESTE.HREF = @Value(neste.href)   # neste.href
- OMR = @Value(omr)   # omr
- OMRNVN = @Value(omrNvn)   # omrNvn
- namespace = vegvesen.no.nvdb   # Namespace

_Input (input)
    -> HTTPCaller_2
Loop (input)
    -> HTTPCaller_2
HTTPCaller_2
    STATUS_CODE_ATTR = _http_status_code
    TARGET_ATTR = _url_contents
    SAVE_FILE = Attribute
    VERIFY_SSL_CERTIFICATES = Yes
    ERROR_ATTR = _error
    TARGET_URL = @Value(neste.href)
    RESPONSE_HEADER_LIST_ATTR = _headers
    HTTP_METHOD = GET
    USE_COOKIES = No
    TRANSFER_TIMEOUT_LENGTH = 90
    CUSTOM_HEADERS = Accept;application/vnd.vegvesen.nvdb-v2+xml
    TARGET_ATTR_ENCODING = auto-detect
    FOLLOW_REDIRECTS = Yes
    CONNECTION_TIMEOUT_LENGTH = 60
    -> XMLFragmenter_2
    -> XMLFragmenter
Note: Deler opp i en XML pr vegobjekt
XMLFragmenter
    MERGE_ATTRS = No
    NEW_ATTRIBUTES = id geometri.wkt startnode sluttnode veglenkeid
    ATTRIBUTE_XML = _url_contents
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    EMBEDDED_EXPRESSIONS = lenke
    XML_SOURCE_TYPE = Attribute with XML document
    FRAGMENTS -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id epsg detaljnivå startposisjon sluttposisjon datafangstdato medium kvalitet.Posisjonskvalitet.synbarhet temakode
    PYTHONSOURCE:
      import fme
      import fmeobjects

      def extractNVDB_XML(feature):

          #Namespace
          ns= 'vegvesen.no.nvdb'

          # Setter feature type
          ft='Veglenke'
          feature.setAttribute('fme_feature_type',ft)
          # ID og versjon.  Namespace ...rls for veglenkesekvenser (id på lenkene er lenkesekvensen sin id)
          feature.setAttribute('identifikasjon.Identifikasjon.navnerom', ns + '.rls')
          v=feature.getAttribute('veglenkeid')
          feature.setAttribute('NVDB_ID', v)
          feature.setAttribute('identifikasjon.Identifikasjon.lokalId', v)
          feature.setAttribute('gml_id', ns + '.rls.' + v)
          # feature.removeAttribute('veglenkeid')

          #LR-info
          feature.setAttribute('standardLRM', 'normalisert')
          # startposisjon og sluttposisjon må tolkes fra evt eksponentielle tall
          v=feature.getAttribute('startposisjon')
          feature.setAttribute('startposisjon', float(v))
          v=feature.getAttribute('sluttposisjon')
          feature.setAttribute('sluttposisjon', float(v))

          #Topologi
          #detaljnivå
          #    <topologinivå>1</topologinivå>
          #    <topologinivå_tekst>Kjørebane</topologinivå_tekst>
          v=feature.getAttribute('topologinivå')
          if v != None:
              #print v
              if v == '0':
                  feature.setAttribute('detaljnivå', 'vegtrase')
              if v == '1':
                  feature.setAttribute('detaljnivå', 'kjørebane')
              if v == '2':
                  feature.setAttribute('detaljnivå', 'kjørefelt')
              feature.removeAttribute('topologinivå_tekst')
             #feature.removeAttribute('topologinivå')

          #noder
          #    <startnode>2373197-1</startnode>
          v=str(feature.getAttribute('startnode'))
          feature.removeAttribute('startnode')
          if v != 'None':
              feature.setAttribute('startnode.xlink_href', '#' + ns + '.rn.' + v)
              feature.setAttribute('startnodeId', v)
          #    <sluttnode>1087601-2</sluttnode>
          v=str(feature.getAttribute('sluttnode'))
          feature.removeAttribute('sluttnode')
          if v != 'None':
              feature.setAttribute('sluttnode.xlink_href', '#' + ns + '.rn.' + v)
              feature.setAttribute('sluttnodeId', v)

          #medium
          #    <medium>T</medium> er riktig :)
          #konnekteringslenke
          #    <konnekteringslenke>false</konnekteringslenke> er riktig :)

          #Kvalitet
          #            <metode>60</metode>
          v=str(feature.getAttribute('geometri.kvalitet.metode'))
          if v != 'None' and v != '-1':
              feature.setAttribute('kvalitet.Posisjonskvalitet.målemetode', v)
          feature.removeAttribute('geometri.kvalitet.metode')
          #            <nøyaktighet>200</nøyaktighet>
          v=str(feature.getAttribute('geometri.kvalitet.nøyaktighet'))
          if v != 'None' and v != '-1':
              feature.setAttribute('kvalitet.Posisjonskvalitet.nøyaktighet', v)
          feature.removeAttribute('geometri.kvalitet.nøyaktighet')
          #            <høydenøyaktighet>-1</høydenøyaktighet>
          v=str(feature.getAttribute('geometri.kvalitet.høydenøyaktighet'))
          if v != 'None' and v != '-1':
              feature.setAttribute('kvalitet.Posisjonskvalitet.nøyaktighetHøyde', v)
          feature.removeAttribute('geometri.kvalitet.høydenøyaktighet')
          #            <toleranse>-1</toleranse>
          v=str(feature.getAttribute('geometri.kvalitet.toleranse'))
          if v != 'None' and v != '-1':
              feature.setAttribute('kvalitet.Posisjonskvalitet.maksimaltAvvik', v)
          feature.removeAttribute('geometri.kvalitet.toleranse')
          #            <synlighet>99</synlighet>
          v=str(feature.getAttribute('geometri.kvalitet.synlighet'))
          if v == '0' or v == '1' or v == '2' or v == '3' :
              feature.setAttribute('kvalitet.Posisjonskvalitet.synbarhet', v)
          feature.removeAttribute('geometri.kvalitet.synlighet')
          #            <datafangstdato>2002-12-07</datafangstdato>
          v=str(feature.getAttribute('geometri.kvalitet.datafangstdato'))
          if v != 'None' and v != '-1':
              feature.setAttribute('datafangstdato', v)
          feature.removeAttribute('geometri.kvalitet.datafangstdato')

          # Geometri
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Vegreferanse
          # <vegreferanse>
          #    <fylke>5</fylke>
          v=str(feature.getAttribute('vegreferanse.fylke'))
          if v != 'None' and v != '0':
              feature.setAttribute('vegreferanse.Vegreferanse.fylkesnummer', v.zfill(2))
          feature.removeAttribute('vegreferanse.fylke')
          #    <kommune>520</kommune>
          v=str(feature.getAttribute('vegreferanse.kommune'))
          if v != 'None' and v != '0':
              feature.setAttribute('vegreferanse.Vegreferanse.kommunenummer', v.zfill(4))
          feature.removeAttribute('vegreferanse.kommune')
          #    <kategori>K</kategori>
          v=str(feature.getAttribute('vegreferanse.kategori'))
          if v != 'None':
              feature.setAttribute('vegreferanse.Vegreferanse.vegkategori', v)
          feature.removeAttribute('vegreferanse.kategori')
          #    <status>V</status>
          v=str(feature.getAttribute('vegreferanse.status'))
          if v != 'None':
              feature.setAttribute('vegreferanse.Vegreferanse.vegstatus', v)
          feature.removeAttribute('vegreferanse.status')
          #    <nummer>1161</nummer>
          v=str(feature.getAttribute('vegreferanse.nummer'))
          if v != 'None':
              feature.setAttribute('vegreferanse.Vegreferanse.vegnummer', v)
          feature.removeAttribute('vegreferanse.nummer')
          #    <hp>1</hp>
          v=str(feature.getAttribute('vegreferanse.hp'))
          if v != 'None':
              feature.setAttribute('vegreferanse.Vegreferanse.hovedparsell', v)
          feature.removeAttribute('vegreferanse.hp')
          #    <fra_meter>57</fra_meter>
          f=str(feature.getAttribute('vegreferanse.fra_meter'))
          if f != 'None':
              feature.setAttribute('vegreferanse.Vegreferanse.veglenkeMeterFra', f)
          feature.removeAttribute('vegreferanse.fra_meter')
          #    <til_meter>96</til_meter>
          t=str(feature.getAttribute('vegreferanse.til_meter'))
          if t != 'None':
              feature.setAttribute('vegreferanse.Vegreferanse.veglenkeMeterTil', t)
          feature.removeAttribute('vegreferanse.til_meter')
          #    <kortform>0520 Kv1161 hp1 m57-96</kortform>
          if f!='None' and t!='None':
              if int(f) <= int(t):
                  feature.setAttribute('vegreferanse.Vegreferanse.referanseretning', 'med')
              else:
                  feature.setAttribute('vegreferanse.Vegreferanse.referanseretning', 'mot')
          # </vegreferanse>
    PYTHONSYMBOL = extractNVDB_XML
    -> GeometryReplacer
Note: Geometri
GeometryReplacer
    REMOVE_ATTRIBUTE = Yes
    OGC_WKT_PRECISION_DISPLAY = 64-bit
    SOURCE = @Value(geometri)
    KIND_LONG = OGC Well Known Text
    -> CoordinateSystemSetter
CoordinateSystemSetter
    COORDSYS = @Value(epsg)
    -> GeometryPropertySetter_4
Note: Definerer geometriegenskap
GeometryPropertySetter_4
    GEOM_NAME_FIELD = senterlinje
    OVERWRITE_CHOICE = Yes
    SETTYPE_PARAM = Geometry Name
    SET -> DateFormatter
DateFormatter
    DATE_ATTR = datafangstdato
    INVALID_DATE_VALUE = _FME_NO_OP_
    SRCFMT = Unknown - Automatic Detection
    FMT = ISO DateTime (%Y-%m-%dT%H:%M:%S)
    -> AttributeValueMapper
Note: Oversetter medium fra initialverdier til kodetekst
AttributeValueMapper
    DEFAULT_VALUE = _FME_NO_OP_
    SRC = medium
    DIRECTION = Forward (Source To Destination)
    VAL_ATTR = medium
    LUT = B,iBygning,D,tidvisUnderVann,I,påIsbre,J,underIsbre,L,iLuft,O,påVannoverflaten,S,påSjøbunnen,T,påTerrenget,U,underTerrenget,V,alltidIVann,W,underSjøbunnen,X,ukjent
    -> AttributeValueMapper_2
Note: Oversetter synbarhet fra initialverdier til kodetekst
AttributeValueMapper_2
    DEFAULT_VALUE = _FME_NO_OP_
    SRC = kvalitet.Posisjonskvalitet.synbarhet
    DIRECTION = Forward (Source To Destination)
    VAL_ATTR = kvalitet.Posisjonskvalitet.synbarhet
    LUT = 0,fulltSynligOgGjenfinnbarITerrenget,1,dårligGjenfinnbarITerrenget,2,middelsSynligIFlybilde,3,dårligSynligIFlybilde
    -> AttributeCreator_2
AttributeRemover
    LIST_ATTRS = lenke{}
    -> Veglenke (output)
Veglenke (output)
XMLFragmenter_2
    MERGE_ATTRS = No
    NEW_ATTRIBUTES = returnert neste.href
    ATTRIBUTE_XML = _url_contents
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    EMBEDDED_EXPRESSIONS = side/metadata
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Midlertidig løsning for typeVeg
Note: Midlertidig løsning for typeVeg: / Setter alle til enkelBilveg
AttributeCreator_2
    ATTR_TABLE = SET_TO typeVeg = enkelBilveg
    -> AttributeRemover

FME custom transformer NVDB_Leser
Leser og tolker data fra NVDB-API

Parameters:
- NESTE.HREF = @Value(neste.href)   # neste.href

_Input (input)
    -> HTTPCaller_2
Loop (input)
    -> HTTPCaller_2
Note: Kan det defineres at et element SKAL blli en liste? Vil i så fall kunne forenkle koden i NVDBTranslator mye. / Se under cardinality under dokumentasjon i XML Fragmenter / https://knowledge.safe.com/idea/36634/better-and-more-consistent-support-for-listscollec.html / cardinality="*/*{?}/+{}"
HTTPCaller_2
    STATUS_CODE_ATTR = _http_status_code
    TARGET_ATTR = _url_contents
    SAVE_FILE = Attribute
    VERIFY_SSL_CERTIFICATES = Yes
    ERROR_ATTR = _error
    TARGET_URL = @Value(neste.href)
    RESPONSE_HEADER_LIST_ATTR = _headers
    HTTP_METHOD = GET
    USE_COOKIES = No
    TRANSFER_TIMEOUT_LENGTH = 90
    CUSTOM_HEADERS = Accept;application/vnd.vegvesen.nvdb-v2+xml
    TARGET_ATTR_ENCODING = auto-detect
    FOLLOW_REDIRECTS = Yes
    CONNECTION_TIMEOUT_LENGTH = 60
    -> XMLFragmenter_2
    -> XMLFragmenter
    <Rejected> -> HTTPCaller_Rejected
Note: Deler opp i en XML pr vegobjekt
XMLFragmenter
    MERGE_ATTRS = No
    NEW_ATTRIBUTES = id geometri.wkt
    ATTRIBUTE_XML = _url_contents
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    EMBEDDED_EXPRESSIONS = vegobjekt
    XML_SOURCE_TYPE = Attribute with XML document
    FRAGMENTS -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg lokasjon.stedfestinger.stedfesting.veglenkeid lokasjon.stedfestinger.stedfesting.fra_posisjon lokasjon.stedfestinger.stedfesting.til_posisjon
    PYTHONSOURCE:
      import fme
      import fmeobjects

      def extractNVDB_XML(feature):

          ns='vegvesen.no.nvdb'

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      # if (n == 'Kommunenummer' and v == 0):
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute('lineærPosisjon{%d}.LineærPosisjonStrekning.nettverkselement.xlink_href' % i, 'Veglenker.gml#' + ns + '.rl.' + v)
                              feature.setAttribute('lineærPosisjon{%d}.LineærPosisjonStrekning.nettverkselement.id' % i, v)
                          v = str(feature.getAttribute('lokasjon.stedfestinger.stedfesting.fra_posisjon'))
                          if v != 'None':
                              feature.setAttribute('lineærPosisjon{%d}.LineærPosisjonStrekning.fraPosisjon' % i, v)
                          v = str(feature.getAttribute('lokasjon.stedfestinger.stedfesting.til_posisjon'))
                          if v != 'None':
                              feature.setAttribute('lineærPosisjon{%d}.LineærPosisjonStrekning.tilPosisjon' % i, v)

                          v = str(feature.getAttribute('lokasjon.stedfestinger.stedfesting.sideposisjon'))
                          if v != 'None':
                              feature.setAttribute('lineærPosisjon{%d}.LineærPosisjonStrekning.sideposisjon' % i, v)

                          v = str(feature.getAttribute('lokasjon.stedfestinger.stedfesting.retning'))
                          if v != 'None':
                              feature.setAttribute('lineærPosisjon{%d}.LineærPosisjonStrekning.retning' % i, v.lower())
                          feature.setAttribute('lineærPosisjon{%d}.LineærPosisjonStrekning.lineærReferanseMetode' % i, 'normalisert')

                      else:
                          # Punktstedfesting
                          v = str(feature.getAttribute('lokasjon.stedfestinger.stedfesting.veglenkeid'))
                          if v != 'None':
                              feature.setAttribute('lineærPosisjon{%d}.LineærPosisjonPunkt.nettverkselement.xlink_href' % i, 'Veglenker.gml#' + ns + '.rl.' + v)

                          v = str(feature.getAttribute('lokasjon.stedfestinger.stedfesting.posisjon'))
                          if v != 'None':
                              feature.setAttribute('lineærPosisjon{%d}.LineærPosisjonPunkt.posisjon' % i, v)

                          v = str(feature.getAttribute('lokasjon.stedfestinger.stedfesting.sideposisjon'))
                          if v != 'None':
                              feature.setAttribute('lineærPosisjon{%d}.LineærPosisjonPunkt.sideposisjon' % i, v)
                          feature.setAttribute('lineærPosisjon{%d}.LineærPosisjonPunkt.lineærReferanseMetode' % i, 'normalisert')

                      #feature.removeAttribute('lokasjon.stedfestinger.stedfesting.veglenkeid')
                      #feature.removeAttribute('lokasjon.stedfestinger.stedfesting.fra_posisjon')
                      #feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute('lineærPosisjon{%d}.LineærPosisjonStrekning.nettverkselement.xlink_href' % i, 'Veglenker.gml#' + ns + '.rl.' + v)
                          feature.setAttribute('lineærPosisjon{%d}.LineærPosisjonStrekning.nettverkselement.id' % i, v)

                      v = str(feature.getAttribute('lokasjon.stedfestinger.stedfesting{%d}.fra_posisjon' % i))
                      if v != 'None':
                          feature.setAttribute('lineærPosisjon{%d}.LineærPosisjonStrekning.fraPosisjon' % i, v)

                      v = str(feature.getAttribute('lokasjon.stedfestinger.stedfesting{%d}.til_posisjon' % i))
                      if v != 'None':
                          feature.setAttribute('lineærPosisjon{%d}.LineærPosisjonStrekning.tilPosisjon' % i, v)

                      v = str(feature.getAttribute('lokasjon.stedfestinger.stedfesting{%d}.sideposisjon' % i))
                      if v != 'None':
                          feature.setAttribute('lineærPosisjon{%d}.LineærPosisjonStrekning.sideposisjon' % i, v)

                      v = str(feature.getAttribute('lokasjon.stedfestinger.stedfesting{%d}.retning' % i))
                      if v != 'None':
                          feature.setAttribute('lineærPosisjon{%d}.LineærPosisjonStrekning.retning' % i, v.lower())
                      feature.setAttribute('lineærPosisjon{%d}.LineærPosisjonStrekning.lineærReferanseMetode' % i, 'normalisert')

                  else:
                      # Punktstedfesting
                      v = str(feature.getAttribute('lokasjon.stedfestinger.stedfesting{%d}.veglenkeid' % i))
                      if v != 'None':
                          feature.setAttribute('lineærPosisjon{%d}.LineærPosisjonPunkt.nettverkselement.xlink_href' % i, 'Veglenker.gml#' + ns + '.rl.' + v)

                      v = str(feature.getAttribute('lokasjon.stedfestinger.stedfesting{%d}.posisjon' % i))
                      if v != 'None':
                          feature.setAttribute('lineærPosisjon{%d}.LineærPosisjonPunkt.posisjon' % i, v)

                      v = str(feature.getAttribute('lokasjon.stedfestinger.stedfesting{%d}.sideposisjon' % i))
                      if v != 'None':
                          feature.setAttribute('lineærPosisjon{%d}.LineærPosisjonPunkt.sideposisjon' % i, v)
                      feature.setAttribute('lineærPosisjon{%d}.LineærPosisjonPunkt.lineærReferanseMetode' % i, 'normalisert')

                  #feature.removeAttribute('lokasjon.stedfestinger.stedfesting{%d}.veglenkeid' % i)
                  #feature.removeAttribute('lokasjon.stedfestinger.stedfesting{%d}.fra_posisjon' % i)
                  #feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  v = str(feature.getAttribute('lokasjon.vegreferanser.vegreferanse{%d}.kategori' % i))
                  if v != 'None':
                      feature.setAttribute('vegreferanse{%d}.Vegreferanse.vegkategori' % i, v)
                      feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> GeometryReplacer
Note: Geometri
GeometryReplacer
    REMOVE_ATTRIBUTE = Yes
    OGC_WKT_PRECISION_DISPLAY = 64-bit
    SOURCE = @Value(geometri)
    KIND_LONG = OGC Well Known Text
    -> CoordinateSystemSetter
    -> CoordinateSystemSetter_2
CoordinateSystemSetter [off]
    COORDSYS = @Value(epsg)
    -> Deaggregator
CoordinateSystemSetter_2
    COORDSYS = EPSG:6173
    -> Deaggregator
XMLFragmenter_2
    MERGE_ATTRS = No
    NEW_ATTRIBUTES = returnert neste.href
    ATTRIBUTE_XML = _url_contents
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    EMBEDDED_EXPRESSIONS = side/metadata
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)
HTTPCaller_Rejected: Inspector

Bookmark: Splitter multigeometrier
Deaggregator
    GEOM_NAME_FIELD = _geometry_name
    PART_NUMBER_FIELD = _part_number
    ID_SELECTION = ID and Parent ID
    COPY_ATTR = Every Node
    SPLIT_COMPOSITES = No
    PARENT_ID_ATTR = _hierarchy_parent_id
    ID_ATTR = _hierarchy_id
    LIST_ATTR_MODE_LOOKUP = LEAN
    MODE = Flatten One Level
    CHILD_ID_ATTR = _hierarchy_child_id_list
    EXPLODE_INSTANCES = No
    DEAGGREGATED -> NullAttributeMapper
NullAttributeMapper
    NULL_TREATMENT = New Value
    ATTRLIST = _part_number
    SOURCE_ATTR_VAL = Null Empty "Missing (Selected Attributes Only)"
    NEW_VALUE = 0
    ATTRCHOICE = Selected Attributes
    -> StringConcatenator
StringConcatenator
    PARM_LINE = @Value(gml_id)_@Value(_part_number)
    VAL_ATTR = gml_id
    ACTION = Create New Attribute
    -> Output (output)
Output (output)
