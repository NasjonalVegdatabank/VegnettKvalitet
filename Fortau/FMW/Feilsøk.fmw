FME workspace Feilsøk.fmw

Creator
    GEOMTYPE = Geometry Object
    NUM = 1
    CREATED -> HTTPCaller_2
HTTPCaller_2
    VERIFY_SSL_CERTIFICATES = Yes
    TARGET_ATTR = _url_contents
    RESPONSE_HEADER_LIST_ATTR = _headers
    HTTP_METHOD = GET
    FOLLOW_REDIRECTS = Yes
    STATUS_CODE_ATTR = _http_status_code
    USE_COOKIES = No
    TARGET_URL = https://www.utv.vegvesen.no/nvdb/api/v2/vegnett/lenker?antall=5000&fylke=9&start=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
    ERROR_ATTR = _error
    TARGET_ATTR_ENCODING = auto-detect
    CONNECTION_TIMEOUT_LENGTH = 60
    CUSTOM_HEADERS = Accept;application/vnd.vegvesen.nvdb-v2+xml
    TRANSFER_TIMEOUT_LENGTH = 90
    SAVE_FILE = Attribute
    -> XMLFragmenter
Note: Deler opp i en XML pr vegobjekt
XMLFragmenter
    XML_SOURCE_TYPE = Attribute with XML document
    FLATTEN_OPTIONS = <structure separator="." map-empty-elements="yes" matched-prefix="attributes" matched-attributes="yes" cardinality="+{?}" structure-prefix="" child-position-attribute="" except-expression="" ui-mode="basic" matched-ancestor-attributes=""/>
    FEATURE_TYPES_FORMAT_NAME = XML
    EMBEDDED_EXPRESSIONS = lenke
    ATTRIBUTE_XML = _url_contents
    MERGE_ATTRS = No
    NEW_ATTRIBUTES = id geometri.wkt startnode sluttnode veglenkeid
    FRAGMENTS -> Sampler
    FRAGMENTS -> NVDBTranslator [off]
Sampler
    SAMPLE_TYPE_LONG = First N Features
    RATE = 352
    SAMPLE_MODE = No
    NOT_SAMPLED -> Sampler_2
Sampler_2
    SAMPLE_TYPE_LONG = First N Features
    RATE = 1
    SAMPLE_MODE = No
    SAMPLED -> Sampler_2_Sampled
    SAMPLED -> NVDBTranslator
Note: Oversetter fra NVDB-API-XML
NVDBTranslator: PythonCaller
    PYTHONSOURCE:
      import fme
      import fmeobjects

      def extractNVDB_XML(feature):

          #Namespace
          ns= 'vegvesen.no.nvdb'

          # Setter feature type
          ft='Veglenke'
          feature.setAttribute('fme_feature_type',ft)
          # ID og versjon.  Namespace ...rls for veglenkesekvenser (id på lenkene er lenkesekvensen sin id)
          feature.setAttribute('identifikasjon.Identifikasjon.navnerom', ns + '.rls')
          v=feature.getAttribute('veglenkeid')
          feature.setAttribute('NVDB_ID', v)
          feature.setAttribute('identifikasjon.Identifikasjon.lokalId', v)
          feature.setAttribute('gml_id', ns + '.rls.' + v)
          # feature.removeAttribute('veglenkeid')

          #LR-info
          feature.setAttribute('standardLRM', 'normalisert')
          # startposisjon og sluttposisjon må tolkes fra evt eksponentielle tall
          v=feature.getAttribute('startposisjon')
          feature.setAttribute('startposisjon', float(v))
          v=feature.getAttribute('sluttposisjon')
          feature.setAttribute('sluttposisjon', float(v))

          #Topologi
          #detaljnivå
          #    <topologinivå>1</topologinivå>
          #    <topologinivå_tekst>Kjørebane</topologinivå_tekst>
          v=feature.getAttribute('topologinivå')
          if v != None:
              #print v
              if v == '0':
                  feature.setAttribute('detaljnivå', 'vegtrase')
              if v == '1':
                  feature.setAttribute('detaljnivå', 'kjørebane')
              if v == '2':
                  feature.setAttribute('detaljnivå', 'kjørefelt')
              feature.removeAttribute('topologinivå_tekst')
             #feature.removeAttribute('topologinivå')

          #noder
          #    <startnode>2373197-1</startnode>
          v=str(feature.getAttribute('startnode'))
          feature.removeAttribute('startnode')
          if v != 'None':
              feature.setAttribute('startnode.xlink_href', '#' + ns + '.rn.' + v)
              feature.setAttribute('startnodeId', v)
          #    <sluttnode>1087601-2</sluttnode>
          v=str(feature.getAttribute('sluttnode'))
          feature.removeAttribute('sluttnode')
          if v != 'None':
              feature.setAttribute('sluttnode.xlink_href', '#' + ns + '.rn.' + v)
              feature.setAttribute('sluttnodeId', v)

          #medium
          #    <medium>T</medium> er riktig :)
          #konnekteringslenke
          #    <konnekteringslenke>false</konnekteringslenke> er riktig :)

          #Kvalitet
          #            <metode>60</metode>
          v=str(feature.getAttribute('geometri.kvalitet.metode'))
          if v != 'None' and v != '-1':
              feature.setAttribute('kvalitet.Posisjonskvalitet.målemetode', v)
          feature.removeAttribute('geometri.kvalitet.metode')
          #            <nøyaktighet>200</nøyaktighet>
          v=str(feature.getAttribute('geometri.kvalitet.nøyaktighet'))
          if v != 'None' and v != '-1':
              feature.setAttribute('kvalitet.Posisjonskvalitet.nøyaktighet', v)
          feature.removeAttribute('geometri.kvalitet.nøyaktighet')
          #            <høydenøyaktighet>-1</høydenøyaktighet>
          v=str(feature.getAttribute('geometri.kvalitet.høydenøyaktighet'))
          if v != 'None' and v != '-1':
              feature.setAttribute('kvalitet.Posisjonskvalitet.nøyaktighetHøyde', v)
          feature.removeAttribute('geometri.kvalitet.høydenøyaktighet')
          #            <toleranse>-1</toleranse>
          v=str(feature.getAttribute('geometri.kvalitet.toleranse'))
          if v != 'None' and v != '-1':
              feature.setAttribute('kvalitet.Posisjonskvalitet.maksimaltAvvik', v)
          feature.removeAttribute('geometri.kvalitet.toleranse')
          #            <synlighet>99</synlighet>
          v=str(feature.getAttribute('geometri.kvalitet.synlighet'))
          if v == '0' or v == '1' or v == '2' or v == '3' :
              feature.setAttribute('kvalitet.Posisjonskvalitet.synbarhet', v)
          feature.removeAttribute('geometri.kvalitet.synlighet')
          #            <datafangstdato>2002-12-07</datafangstdato>
          v=str(feature.getAttribute('geometri.kvalitet.datafangstdato'))
          if v != 'None' and v != '-1':
              feature.setAttribute('datafangstdato', v)
          feature.removeAttribute('geometri.kvalitet.datafangstdato')

          # Geometri
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Vegreferanse
          # <vegreferanse>
          #    <fylke>5</fylke>
          v=str(feature.getAttribute('vegreferanse.fylke'))
          if v != 'None' and v != '0':
              feature.setAttribute('vegreferanse.Vegreferanse.fylkesnummer', v.zfill(2))
          feature.removeAttribute('vegreferanse.fylke')
          #    <kommune>520</kommune>
          v=str(feature.getAttribute('vegreferanse.kommune'))
          if v != 'None' and v != '0':
              feature.setAttribute('vegreferanse.Vegreferanse.kommunenummer', v.zfill(4))
          feature.removeAttribute('vegreferanse.kommune')
          #    <kategori>K</kategori>
          v=str(feature.getAttribute('vegreferanse.kategori'))
          if v != 'None':
              feature.setAttribute('vegreferanse.Vegreferanse.vegkategori', v)
          feature.removeAttribute('vegreferanse.kategori')
          #    <status>V</status>
          v=str(feature.getAttribute('vegreferanse.status'))
          if v != 'None':
              feature.setAttribute('vegreferanse.Vegreferanse.vegstatus', v)
          feature.removeAttribute('vegreferanse.status')
          #    <nummer>1161</nummer>
          v=str(feature.getAttribute('vegreferanse.nummer'))
          if v != 'None':
              feature.setAttribute('vegreferanse.Vegreferanse.vegnummer', v)
          feature.removeAttribute('vegreferanse.nummer')
          #    <hp>1</hp>
          v=str(feature.getAttribute('vegreferanse.hp'))
          if v != 'None':
              feature.setAttribute('vegreferanse.Vegreferanse.hovedparsell', v)
          feature.removeAttribute('vegreferanse.hp')
          #    <fra_meter>57</fra_meter>
          f=str(feature.getAttribute('vegreferanse.fra_meter'))
          if f != 'None':
              feature.setAttribute('vegreferanse.Vegreferanse.veglenkeMeterFra', f)
          feature.removeAttribute('vegreferanse.fra_meter')
          #    <til_meter>96</til_meter>
          t=str(feature.getAttribute('vegreferanse.til_meter'))
          if t != 'None':
              feature.setAttribute('vegreferanse.Vegreferanse.veglenkeMeterTil', t)
          feature.removeAttribute('vegreferanse.til_meter')
          #    <kortform>0520 Kv1161 hp1 m57-96</kortform>
          if f!='None' and t!='None':
              if int(f) <= int(t):
                  feature.setAttribute('vegreferanse.Vegreferanse.referanseretning', 'med')
              else:
                  feature.setAttribute('vegreferanse.Vegreferanse.referanseretning', 'mot')
          # </vegreferanse>
    PYTHONSYMBOL = extractNVDB_XML
    NEW_ATTRIBUTES = geometri fme_feature_type identifikasjon.Identifikasjon.lokalId identifikasjon.Identifikasjon.versjonId identifikasjon.Identifikasjon.navnerom gml_id epsg detaljnivå startposisjon sluttposisjon datafangstdato medium kvalitet.Posisjonskvalitet.synbarhet temakode
    -> NVDBTranslator_Output
NVDBTranslator_Output: Inspector [off]
Sampler_2_Sampled: Inspector [off]
