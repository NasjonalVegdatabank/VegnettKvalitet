FME workspace SkiltFeltstrekningKontroll.fmw

Parameters:
- dataFolder = O:\1\Res\16080 Geodata\Fagområde Vegnett\Vegnett spesialistfunksjon\Feil og kvalitetskontroller i NVDB\FME-kontroller\Skilt og feltstrekning\Data   # Mappe for resultatfiler
- today:   # Python Script
      import time
      ## dd/mm/yyyy format
      time.strftime("%Y%m%d")

Writers:
- XLSXW2_1: XLSXW2 to $(dataFolder)\$(today)\SkiltFeltFeil.xls
- SPATIALITE_1: SPATIALITE to $(dataFolder)\$(today)\SkiltFeltFeil.db
- TEXTLINE_1: TEXTLINE to $(dataFolder)\$(today)

TestFilter_2
    DEFAULT_VALUE = <UNFILTERED>
    TEST_LIST = BOOL_OP,OR,COMPOSITE_TEST,<Unused>,TEST_CLAUSE,"TEST @Value(_skiltnummer) = 7707",Sykkelveg
    Sykkelveg -> Feil_skilting
    Sykkelveg -> FeilSkilting (writer XLSXW2_1)
Feil_skilting: Inspector
Note: Feil skilting
FeilSkilting (writer XLSXW2_1)
    attributes: NVDB_ID auto(20), skiltnummer auto(20), fylke auto(20), kommune auto(20), vegkategori auto(20), vegstatus auto(20), vegnummer auto(20), hovedparsell auto(20), meter auto(20), lenkeId auto(20), posisjon auto(20), east auto(20), north auto(20)
Note: Skiltnumre og NVDB-ID: / 7699 = 508.1 - Kollektivfelt, for buss / 7700 = 508.2 - Kollektivfelt for buss og drosje / 9164 = 509 - Sambruksfelt
StringConcatenator
    PARM_LINE = @Value(vegkategori)@Value(vegstatus)@Value(vegnummer)
    VAL_ATTR = vegident
    ACTION = Create New Attribute
    -> FeatureHolder_2
Note: Skiltnumre og NVDB-ID: / 7707 = 520 - Sykkelveg / 9167 = 521 - Sykkelfelt / 13465 = 521.2 - Sykkelfelt, midtstilt / 7706 = 518 Gangveg (tas med pga feil skilting)
FeatureHolder_2
    -> Bufferer
    -> GeometryExtractor
Feltstrekninger: Inspector
Note: Finner vegreferanser
ListExploder_3
    INDEX_ATTR = _element_index
    ATTR_CONFLICT_RES = Use Incoming List
    ATTR_ACCUM_MODE = Merge Incoming List
    LIST_ATTR = vegreferanse{}
    ELEMENTS -> AttributeExposer_2
AttributeExposer_2
    ATTR_LIST = Vegreferanse.fylke,Vegreferanse.kommune,Vegreferanse.vegkategori,Vegreferanse.vegnummer,Vegreferanse.hovedparsell,Vegreferanse.veglenkeMeterFra,Vegreferanse.veglenkeMeterTil,Vegreferanse.vegstatus
    -> AttributeRenamer_3
AttributeRenamer_3
    ATTR_LIST = Vegreferanse.fylke,fylke,,Vegreferanse.kommune,kommune,,Vegreferanse.vegkategori,vegkategori,,Vegreferanse.vegnummer,vegnummer,,Vegreferanse.hovedparsell,hovedparsell,,Vegreferanse.veglenkeMeterFra,meter,,Vegreferanse.vegstatus,vegstatus,
    -> AttributeExposer_3
AttributeExposer_3
    ATTR_LIST = 5528
    -> SpatialRelator [Supplier]
GeometryExtractor
    ATTR = _geometry
    KIND_LONG = FME Binary
    REMOVE_GEOMETRY = No
    -> Bufferer_2
Note: 25 m buffer
Bufferer_2
    INTERP_SEGMENTS = 8
    CAP_STYLE = Round
    OFFSET = 25
    BUFFERED -> SpatialRelator [Requestor]
Note: Finner feltstrekninger i buffer
SpatialRelator
    AGGREGATE_HANDLING = Yes
    LIST_NAME = _relationships
    CALC_CARD = No
    SUCCESS_ATTR = _related_candidates
    GROUP_BY = vegnummer vegstatus vegkategori
    CURVE_BOUNDARY_RULE_PARAM = Default Rule
    PREDICATES = INTERSECTS
    -> ListSearcher
Note: Søk etter feltverdi
ListSearcher
    SEARCH_TYPE = First to contain regular expression
    INDEX_ATTR = _list_index
    ATTR_VALUE = @Value(feltverdi)
    LIST_ATTR = _relationships{}.5528
    NOT_FOUND -> GeometryReplacer
GeometryReplacer
    REMOVE_ATTRIBUTE = Yes
    SOURCE = @Value(_geometry)
    KIND_LONG = FME Binary
    -> Avviksliste (writer XLSXW2_1)
    -> Avvik
    -> AttributeRenamer_2
Avvik: Inspector
    TACKATTRS = skiltnummer tema
Note: Excell
Avviksliste (writer XLSXW2_1)
    attributes: NVDB_ID auto(20), skiltnummer auto(20), fylke auto(20), kommune auto(20), vegkategori auto(20), vegstatus auto(20), vegnummer auto(20), hovedparsell auto(20), meter auto(20), lenkeId auto(20), posisjon auto(20), east auto(20), north auto(20)
AttributeRenamer_2
    ATTR_LIST = NVDB_ID,nvdb_id,,lenkeId,lenkeid,,fme_basename,type,
    -> avviksliste (writer SPATIALITE_1)
    -> StringConcatenator_2
Note: SpatiaLite
avviksliste (writer SPATIALITE_1)
    attributes: nvdb_id real(31,15), skiltnummer string(255), fylke real(31,15), kommune real(31,15), vegkategori string(2), vegstatus string(2), vegnummer real(31,15), hovedparsell real(31,15), meter real(31,15), lenkeid string(8), posisjon string(255), east real(31,15), north real(31,15), type string(31)
StringConcatenator_2
    PARM_LINE = FEIL: @Value(north) @Value(east) Mangler feltkode @Value(feltverdi) ved skilt @Value(skiltnummer), vegreferanse @Value(vegident) hp @Value(hovedparsell) m@Value(meter)
    VAL_ATTR = text_line_data
    ACTION = Create New Attribute
    -> text_line (writer TEXTLINE_1)
Note: Fylkesvise GL Feilfiler
text_line (writer TEXTLINE_1)
    attributes: text_line_data buffer

Bookmark: Kollektivfelt
Creator_2
    NUM = 1
    GEOMTYPE = Geometry Object
    CREATED -> AttributeManager
AttributeManager
    ATTR_TABLE:
      SET_TO tema = Kollektiv
      SET_TO feltverdi = K
      SET_TO skiltnummer = 7699|7700|9164
    -> TimeStamper_3

Bookmark: Sykkelfelt
Creator
    NUM = 1
    GEOMTYPE = Geometry Object
    CREATED -> AttributeManager_2
AttributeManager_2
    ATTR_TABLE:
      SET_TO tema = Sykkel
      SET_TO feltverdi = S
      SET_TO skiltnummer = 7707|9167|13465|7706
    -> TimeStamper_3

Bookmark: Leser skiltplater fra NVDB API
TimeStamper_3
    FMT = FME Date (^Y^m^d)
    TIME_ATTR = _timestamp
    -> AttributeSplitter
AttributeSplitter
    DELIMITER = |
    DROP_EMPTY_PARTS = No
    ATTR_NAME = skiltnummer
    LIST_NAME = _skiltnummer
    TRIM_OPTION = Both
    -> ListExploder
ListExploder
    INDEX_ATTR = _element_index
    ATTR_CONFLICT_RES = Use Original
    ATTR_ACCUM_MODE = Merge Incoming List
    LIST_ATTR = _skiltnummer{}
    ELEMENTS -> AttributeCreator
AttributeCreator
    ATTR_TABLE = SET_TO href = https://www.vegvesen.no/nvdb/api/v2/vegobjekter/96?egenskap="5530=@Value(_skiltnummer)"&antall=5000&inkluder=alle
    -> NVDB_Leser [_Input]
NVDB_Leser
    NESTE.HREF = @Value(href)
    -> ListExploder_4
    -> Skilt
Note: Finner vegreferanser
ListExploder_4
    INDEX_ATTR = _element_index
    ATTR_CONFLICT_RES = Use Incoming List
    ATTR_ACCUM_MODE = Merge Incoming List
    LIST_ATTR = vegreferanse{}
    ELEMENTS -> ListExploder_2
ListExploder_2
    INDEX_ATTR = _element_index
    ATTR_CONFLICT_RES = Use Original
    ATTR_ACCUM_MODE = Merge Incoming List
    LIST_ATTR = lineærPosisjon{}
    ELEMENTS -> AttributeExposer_5
AttributeExposer_5
    ATTR_LIST = Vegreferanse.fylke,Vegreferanse.kommune,Vegreferanse.vegkategori,Vegreferanse.vegnummer,Vegreferanse.hovedparsell,Vegreferanse.veglenkeMeterFra,Vegreferanse.veglenkeMeterTil,Vegreferanse.vegstatus,LineærPosisjonPunkt.posisjon,LineærPosisjonPunkt.nettverkselement.id
    -> AttributeRenamer_4
AttributeRenamer_4
    ATTR_LIST = identifikasjon.Identifikasjon.lokalId,NVDB_ID,,LineærPosisjonPunkt.nettverkselement.id,lenkeId,,Vegreferanse.fylke,fylke,,Vegreferanse.kommune,kommune,,Vegreferanse.vegkategori,vegkategori,,Vegreferanse.vegnummer,vegnummer,,Vegreferanse.hovedparsell,hovedparsell,,Vegreferanse.veglenkeMeterFra,meter,,Vegreferanse.vegstatus,vegstatus,,LineærPosisjonPunkt.posisjon,posisjon,
    -> AttributeValueMapper_3
AttributeValueMapper_3
    SRC = _skiltnummer
    VAL_ATTR = skiltnummer
    DIRECTION = Forward (Source To Destination)
    LUT = 7699,508.1 - Kollektivfelt, for buss,7700,508.2 - Kollektivfelt for buss og drosje,9164,509 - Sambruksfelt,7707,520 - Sykkelveg,9167,521 - Sykkelfelt,13465,521.2 - Sykkelfelt, midtstilt
    -> CoordinateExtractor_2
CoordinateExtractor_2
    X_ATTR = east
    Z_ATTR = _z
    Y_ATTR = north
    MODE = Specify Coordinate
    IND = 0
    -> AttributeFilter
AttributeFilter
    ATTR_VALUES = 7706,7707,<EMPTY>,<MISSING>,<NULL>,<UNFILTERED>
    ATTR_NAME = _skiltnummer
    7706 -> Matcher
    7707 -> Matcher
    <UNFILTERED> -> StringConcatenator
Note: Finner overlapp mellom sykkelvegskilt og gangvegskilt
Matcher
    MATCHATTRS = posisjon lenkeId
    MATCH = 2D
    DIFFATTRS = _skiltnummer
    CNT_ATTR = _match_id
    LENIENT_MATCH = No
    BLANK_AND_MISSING_DIFFER = No
    MATCH_STRATEGY = Match Selected Attributes
    MATCHED -> TestFilter_2
    NOT_MATCHED -> TestFilter
TestFilter
    DEFAULT_VALUE = <UNFILTERED>
    TEST_LIST = BOOL_OP,OR,COMPOSITE_TEST,<Unused>,TEST_CLAUSE,"TEST @Value(_skiltnummer) = 7707",Sykkelveg
    Sykkelveg -> StringConcatenator
Skilt: Inspector [off]
    TACKATTRS = skiltnummer tema

Bookmark: Finner feltstrekningsobjekter med samme vegident innenfor ruter på 500x500m ved skiltene
Bufferer
    INTERP_SEGMENTS = 8
    CAP_STYLE = Square
    LIST_NAME = pnt_List
    OFFSET = 250
    GROUP_BY = fme_feature_type
    BUFFERED -> ListDuplicateRemover
ListDuplicateRemover
    SRC_LIST = pnt_List{}.vegident
    -> ListConcatenator
Note: Vegkategoriutvalg
ListConcatenator
    DROP_EMPTY_PARTS = Yes
    VAL_ATTR = vk_Liste
    SEP = ,
    LIST_ATTR = pnt_List{}.vegident
    -> BoundsExtractor
BoundsExtractor
    ZMAX = _zmax
    XMIN = _xmin
    XMAX = _xmax
    YMAX = _ymax
    ZMIN = _zmin
    YMIN = _ymin
    -> StringReplacer_2
StringReplacer_2
    SRC_ATTRS = epsg
    CASE = NO
    FIND_TEXT = EPSG:
    REGEXP = NO
    NO_MATCH = _FME_NO_OP_
    -> AttributeCreator_4
AttributeCreator_4
    ATTR_TABLE = SET_TO href = https://www.vegvesen.no/nvdb/api/v2/vegobjekter/616?kartutsnitt=@Value(_xmin),@Value(_ymin),@Value(_xmax),@Value(_ymax)&srid=@Value(epsg)&vegreferanse=@Value(vk_Liste)&antall=5000&inkluder=alle
    -> AttributeKeeper_2
AttributeKeeper_2
    KEEP_ATTRS = href
    -> NVDB_Leser_2 [_Input]
NVDB_Leser_2
    NESTE.HREF = @Value(href)
    -> DuplicateFilter
    -> Feltstrekninger
    -> ListExploder_3
DuplicateFilter [off]
    KEYATTR = identifikasjon.Identifikasjon.lokalId identifikasjon.Identifikasjon.versjonId identifikasjon.Identifikasjon.navnerom
    INPUT_ORDERED_CHOICE = No
    UNIQUE -> ListExploder_3

FME custom transformer NVDB_Leser
Leser og tolker data fra NVDB-API

Parameters:
- NESTE.HREF = @Value(neste.href)   # neste.href

_Input (input)
    -> HTTPCaller_2
Loop (input)
    -> HTTPCaller_2
HTTPCaller_2
    STATUS_CODE_ATTR = _http_status_code
    ERROR_ATTR = _error
    HTTP_METHOD = GET
    TARGET_URL = @Value(neste.href)
    CONNECTION_TIMEOUT_LENGTH = 60
    FOLLOW_REDIRECTS = Yes
    RESPONSE_HEADER_LIST_ATTR = _headers
    VERIFY_SSL_CERTIFICATES = Yes
    TARGET_ATTR = _url_contents
    CUSTOM_HEADERS = Accept;application/vnd.vegvesen.nvdb-v2+xml
    SAVE_FILE = Attribute
    USE_COOKIES = No
    TARGET_ATTR_ENCODING = auto-detect
    TRANSFER_TIMEOUT_LENGTH = 90
    -> XMLFragmenter_2
    -> XMLFragmenter
Note: Deler opp i en XML pr vegobjekt
Note: Kan det defineres at et element SKAL blli en liste? Vil i så fall kunne forenkle koden i NVDBTranslator mye. / Se under cardinality under dokumentasjon i XML Fragmenter
XMLFragmenter
    ATTRIBUTE_XML = _url_contents
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = id geometri.wkt
    FEATURE_TYPES_FORMAT_NAME = XML
    EMBEDDED_EXPRESSIONS = vegobjekt
    XML_SOURCE_TYPE = Attribute with XML document
    MERGE_ATTRS = Yes
    FRAGMENTS -> AttributeRemover
AttributeRemover
    REMOVE_ATTRS = _url_contents
    -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg vegreferanse{} lineærPosisjon{}
    PYTHONSOURCE:
      import fme
      import fmeobjects

      def extractNVDB_XML(feature):

          ns= 'vegvesen.no.nvdb' #FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute('lineærPosisjon{%d}.LineærPosisjonStrekning.nettverkselement.xlink_href' % i, 'Veglenker.gml#' + ns + '.rl.' + v)
                          v = str(feature.getAttribute('lokasjon.stedfestinger.stedfesting.fra_posisjon'))
                          if v != 'None':
                              feature.setAttribute('lineærPosisjon{%d}.LineærPosisjonStrekning.fraPosisjon' % i, v)
                          v = str(feature.getAttribute('lokasjon.stedfestinger.stedfesting.til_posisjon'))
                          if v != 'None':
                              feature.setAttribute('lineærPosisjon{%d}.LineærPosisjonStrekning.tilPosisjon' % i, v)

                          v = str(feature.getAttribute('lokasjon.stedfestinger.stedfesting.sideposisjon'))
                          if v != 'None':
                              feature.setAttribute('lineærPosisjon{%d}.LineærPosisjonStrekning.sideposisjon' % i, v)

                          v = str(feature.getAttribute('lokasjon.stedfestinger.stedfesting.retning'))
                          if v != 'None':
                              feature.setAttribute('lineærPosisjon{%d}.LineærPosisjonStrekning.retning' % i, v.lower())
                          feature.setAttribute('lineærPosisjon{%d}.LineærPosisjonStrekning.lineærReferanseMetode' % i, 'normalisert')

                      else:
                          # Punktstedfesting
                          v = str(feature.getAttribute('lokasjon.stedfestinger.stedfesting.veglenkeid'))
                          if v != 'None':
                              feature.setAttribute('lineærPosisjon{%d}.LineærPosisjonPunkt.nettverkselement.xlink_href' % i, 'Veglenker.gml#' + ns + '.rl.' + v)
                              feature.setAttribute('lineærPosisjon{%d}.LineærPosisjonPunkt.nettverkselement.id' % i, v)
                          v = str(feature.getAttribute('lokasjon.stedfestinger.stedfesting.posisjon'))
                          if v != 'None':
                              feature.setAttribute('lineærPosisjon{%d}.LineærPosisjonPunkt.posisjon' % i, v)

                          v = str(feature.getAttribute('lokasjon.stedfestinger.stedfesting.sideposisjon'))
                          if v != 'None':
                              feature.setAttribute('lineærPosisjon{%d}.LineærPosisjonPunkt.sideposisjon' % i, v)
                          feature.setAttribute('lineærPosisjon{%d}.LineærPosisjonPunkt.lineærReferanseMetode' % i, 'normalisert')

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute('lineærPosisjon{%d}.LineærPosisjonStrekning.nettverkselement.xlink_href' % i, 'Veglenker.gml#' + ns + '.rl.' + v)

                      v = str(feature.getAttribute('lokasjon.stedfestinger.stedfesting{%d}.fra_posisjon' % i))
                      if v != 'None':
                          feature.setAttribute('lineærPosisjon{%d}.LineærPosisjonStrekning.fraPosisjon' % i, v)

                      v = str(feature.getAttribute('lokasjon.stedfestinger.stedfesting{%d}.til_posisjon' % i))
                      if v != 'None':
                          feature.setAttribute('lineærPosisjon{%d}.LineærPosisjonStrekning.tilPosisjon' % i, v)

                      v = str(feature.getAttribute('lokasjon.stedfestinger.stedfesting{%d}.sideposisjon' % i))
                      if v != 'None':
                          feature.setAttribute('lineærPosisjon{%d}.LineærPosisjonStrekning.sideposisjon' % i, v)

                      v = str(feature.getAttribute('lokasjon.stedfestinger.stedfesting{%d}.retning' % i))
                      if v != 'None':
                          feature.setAttribute('lineærPosisjon{%d}.LineærPosisjonStrekning.retning' % i, v.lower())
                      feature.setAttribute('lineærPosisjon{%d}.LineærPosisjonStrekning.lineærReferanseMetode' % i, 'normalisert')

                  else:
                      # Punktstedfesting
                      v = str(feature.getAttribute('lokasjon.stedfestinger.stedfesting{%d}.veglenkeid' % i))
                      if v != 'None':
                          feature.setAttribute('lineærPosisjon{%d}.LineærPosisjonPunkt.nettverkselement.xlink_href' % i, 'Veglenker.gml#' + ns + '.rl.' + v)
                          feature.setAttribute('lineærPosisjon{%d}.LineærPosisjonPunkt.nettverkselement.id' % i, v)
                      v = str(feature.getAttribute('lokasjon.stedfestinger.stedfesting{%d}.posisjon' % i))
                      if v != 'None':
                          feature.setAttribute('lineærPosisjon{%d}.LineærPosisjonPunkt.posisjon' % i, v)

                      v = str(feature.getAttribute('lokasjon.stedfestinger.stedfesting{%d}.sideposisjon' % i))
                      if v != 'None':
                          feature.setAttribute('lineærPosisjon{%d}.LineærPosisjonPunkt.sideposisjon' % i, v)
                      feature.setAttribute('lineærPosisjon{%d}.LineærPosisjonPunkt.lineærReferanseMetode' % i, 'normalisert')

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  feature.setAttribute('vegreferanse{%d}.Vegreferanse.vegkategori' % i, v)
                  feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> AttributeFilter
AttributeFilter
    ATTR_VALUES = <EMPTY>,<MISSING>,<NULL>,<UNFILTERED>
    ATTR_NAME = geometri
    <UNFILTERED> -> GeometryReplacer
Note: Geometri
GeometryReplacer
    OGC_WKT_PRECISION_DISPLAY = 64-bit
    REMOVE_ATTRIBUTE = Yes
    SOURCE = @Value(geometri)
    KIND_LONG = OGC Well Known Text
    -> CoordinateSystemSetter
    -> CoordinateSystemSetter_2
CoordinateSystemSetter
    COORDSYS = @Value(epsg)
    -> Deaggregator
CoordinateSystemSetter_2 [off]
    COORDSYS = EPSG:25833
    -> Deaggregator
XMLFragmenter_2
    ATTRIBUTE_XML = _url_contents
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = returnert neste.href
    FEATURE_TYPES_FORMAT_NAME = XML
    EMBEDDED_EXPRESSIONS = side/metadata
    XML_SOURCE_TYPE = Attribute with XML document
    MERGE_ATTRS = No
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Splitter multigeometrier
Deaggregator
    SPLIT_COMPOSITES = No
    EXPLODE_INSTANCES = No
    LIST_ATTR_MODE_LOOKUP = LEAN
    ID_SELECTION = ID and Parent ID
    COPY_ATTR = Every Node
    CHILD_ID_ATTR = _hierarchy_child_id_list
    MODE = Flatten One Level
    PART_NUMBER_FIELD = _part_number
    PARENT_ID_ATTR = _hierarchy_parent_id
    ID_ATTR = _hierarchy_id
    GEOM_NAME_FIELD = _geometry_name
    DEAGGREGATED -> NullAttributeMapper
NullAttributeMapper
    SOURCE_ATTR_VAL = Null Empty "Missing (Selected Attributes Only)"
    ATTRCHOICE = Selected Attributes
    NULL_TREATMENT = New Value
    ATTRLIST = _part_number
    NEW_VALUE = 0
    -> StringConcatenator
StringConcatenator
    PARM_LINE = @Value(gml_id)_@Value(_part_number)
    VAL_ATTR = gml_id
    ACTION = Create New Attribute
    -> Output (output)
Output (output)
