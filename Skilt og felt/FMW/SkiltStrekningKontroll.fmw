FME workspace SkiltStrekningKontroll.fmw

Parameters:
- dataFolder = O:\1\Res\16080 Geodata\Fagområde Vegnett\Vegnett spesialistfunksjon\Feil og kvalitetskontroller i NVDB\FME-kontroller\Skilt og felt\Data   # Mappe for resultatfiler
- xfmap_api = O:\1\Res\16080 Geodata\Fagområde Vegnett\Vegnett spesialistfunksjon\Feil og kvalitetskontroller i NVDB\FME-kontroller\Felles\API_Mapping.xmp   # xfMap for API-mapping
- coordsys = EPSG:25833   # Koordinatsystem
- maxFeatures = 10000   # Maximal number of features
- lokasjon = "land":["Norge"]   # Lokasjonsutvalg

Writers:
- XLSXW2_1: XLSXW2 to $(dataFolder)
- SPATIALITE_1: SPATIALITE to $(dataFolder)

AttributeExposer
    ATTR_LIST = NVDB_ID
    -> BulkAttributeRenamer
BulkAttributeRenamer
    ATTRCHOICE = ALL
    MODE_CHOICE = RENAME
    REPLACE_STR = skilt_
    PATTERN_ACTION_DISP = ADDPREFIX
    -> Bufferer
    -> FeatureMerger [REQUESTOR]
    -> Skilt
Skilt: Inspector [off]
Bufferer
    OFFSET = 25
    CAP_STYLE = Square
    INTERP_SEGMENTS = 8
    BUFFERED -> BoundsExtractor
BoundsExtractor
    ZMAX = _zmax
    YMIN = _ymin
    XMIN = _xmin
    XMAX = _xmax
    ZMIN = _zmin
    YMAX = _ymax
    -> HTTPFetcher_3
Note: Henter feltstrekningsobjekter fra NVDB-API
HTTPFetcher_3
    PROXY_AUTH_METHOD = Basic
    TARGET_ATTR = _url_contents
    TRANSFER_TIMEOUT_LENGTH = 90
    ERROR_ATTR = _error
    USE_COOKIES = No
    REQUEST_HEADER:
      GET /vegobjekter HTTP/1.1
      Accept: application/vnd.vegvesen.nvdb-v1+xml
    CONNECTION_TIMEOUT_LENGTH = 60
    SAVE_FILE = No
    STATUS_CODE_ATTR = _http_status_code
    TARGET_URL = https://www.vegvesen.no/nvdb/api/sok?kriterie={"lokasjon":{"bbox":"@Value(_xmin),@Value(_ymin),@Value(_xmax),@Value(_ymax)"},"objektTyper":[{"id":616,"antall":"1000","filter":[]}]}
    FOLLOW_REDIRECTS = Yes
    RESPONSE_HEADER_LIST_ATTR = _headers
    VERIFY_SSL_CERTIFICATES = Yes
    -> XMLFeatureMapper_2
Note: Tolker XML
XMLFeatureMapper_2
    FEATURE_TYPE_ATTR = fme_feature_type
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt
    XML_SOURCE_NAME = _xml_source_
    CONFIGURATION_TYPE = Single xfMap file
    XML_INPUT_TYPE = Attribute with XML document
    FEATURE_COUNT_PER_XML = _xml_feature_count_
    ATTRIBUTE_XML = _url_contents
    MERGE_ATTRS = Yes
    SINGLE_XFMAP = $(xfmap_api)
    MAPPED -> GeometryReplacer_2
    MAPPED -> AttributeExposer_2
Note: Tildeler geometri
GeometryReplacer_2 [off]
    REMOVE_ATTRIBUTE = Yes
    OGC_WKT_PRECISION_DISPLAY = 64-bit
    KIND_LONG = OGC Well Known Text
    SOURCE = @Value(geometriUtm33)
    -> CoordinateSystemSetter_2 [off]
CoordinateSystemSetter_2 [off]
    COORDSYS = $(coordsys)
    -> AttributeExposer_2 [off]
    -> Strekninger
AttributeExposer_2
    ATTR_LIST = 5528
    -> StringSearcher
StringSearcher
    MATCHED_PARTS_ATTR = _matched_parts
    CASE = no
    STRING_TO_SEARCH = @Value(5528)
    MATCHED_RESULT_ATTR = _matched_characters
    REGEXP = S
    MATCHED -> FeatureMerger [SUPPLIER]
FeatureMerger
    MERGE_TYPE = Attributes Only
    SUPPLIERS_FIRST = No
    IGNORE_NULLS = No
    JOIN_KEYS = @Value(skilt_NVDB_ID) @Value(skilt_NVDB_ID) AUTO
    ATTR_ACCUM_MODE = Merge Supplier
    ATTR_CONFLICT_RES = Use Requestor
    PROCESS_DUPS = No
    NOT_MERGED -> ListExploder_2
ListExploder_2
    ATTR_ACCUM_MODE = Merge Incoming List
    INDEX_ATTR = _element_index
    LIST_ATTR = skilt_vegreferanse{}
    ATTR_CONFLICT_RES = Use Original
    ELEMENTS -> ListExploder_3
ListExploder_3
    ATTR_ACCUM_MODE = Merge Incoming List
    INDEX_ATTR = _element_index
    LIST_ATTR = skilt_lineærPosisjon{}
    ATTR_CONFLICT_RES = Use Original
    ELEMENTS -> AttributeExposer_3
AttributeExposer_3
    ATTR_LIST = Vegreferanse.fylke,Vegreferanse.kommune,Vegreferanse.vegkategori,Vegreferanse.vegnummer,Vegreferanse.hovedParsell,Vegreferanse.veglenkeMeterFra,Vegreferanse.veglenkeMeterTil,Vegreferanse.vegstatus
    -> AttributeRenamer
AttributeRenamer
    ATTR_LIST = skilt__x,east,,skilt_NVDB_ID,NVDB_ID,,lineærtObjektIdentifikasjon.Identifikasjon.lokalId,lenkeId,,skilt__skiltnummer,skiltnummer,,skilt__y,north,,fraPosisjon,posisjon,,Vegreferanse.fylke,fylke,,Vegreferanse.kommune,kommune,,Vegreferanse.vegkategori,vegkategori,,Vegreferanse.vegnummer,vegnummer,,Vegreferanse.hovedParsell,hovedParsell,,Vegreferanse.veglenkeMeterFra,meter,,Vegreferanse.vegstatus,vegstatus,
    -> Avviksliste (writer XLSXW2_1)
    -> AttributeRenamer_2
Avviksliste (writer XLSXW2_1)
    attributes: NVDB_ID auto(20), skiltnummer auto(20), fylke auto(20), kommune auto(20), vegkategori auto(20), vegstatus auto(20), vegnummer auto(20), hovedParsell auto(20), meter auto(20), lenkeId auto(20), posisjon auto(20), east auto(20), north auto(20)
AttributeRenamer_2
    ATTR_LIST = NVDB_ID,nvdb_id,,hovedParsell,hovedparsell,,lenkeId,lenkeid,,fme_basename,type,
    -> avviksliste (writer SPATIALITE_1)
avviksliste (writer SPATIALITE_1)
    attributes: nvdb_id real(31,15), skiltnummer string(255), fylke real(31,15), kommune real(31,15), vegkategori string(2), vegstatus string(2), vegnummer real(31,15), hovedparsell real(31,15), meter real(31,15), lenkeid string(8), posisjon string(255), east real(31,15), north real(31,15), type string(31)
Strekninger: Inspector [off]

Bookmark: Kollektivfelt
Creator_2
    GEOMTYPE = Geometry Object
    NUM = 1
    CREATED -> AttributeManager
AttributeManager
    ATTR_TABLE:
      SET_TO tema = Kollektiv
      SET_TO feltverdi = K
      SET_TO skiltnummer = 508.1 - Kollektivfelt, for buss|508.2 - Kollektivfelt for buss og drosje|509 - Sambruksfelt
    -> AttributeSplitter

Bookmark: Sykkelfelt
Creator
    GEOMTYPE = Geometry Object
    NUM = 1
    CREATED -> AttributeManager_2
AttributeManager_2
    ATTR_TABLE:
      SET_TO tema = Sykkel
      SET_TO feltverdi = S
      SET_TO skiltnummer = 520 - Sykkelveg|521 - Sykkelfelt|521.2 - Sykkelfelt, midtstilt
    -> AttributeSplitter

Bookmark: Leser skiltplater fra NVDB API
AttributeSplitter
    ATTR_NAME = skiltnummer
    TRIM_OPTION = Both
    DROP_EMPTY_PARTS = No
    LIST_NAME = _skiltnummer
    DELIMITER = |
    -> ListExploder
ListExploder
    ATTR_ACCUM_MODE = Merge Incoming List
    INDEX_ATTR = _element_index
    LIST_ATTR = _skiltnummer{}
    ATTR_CONFLICT_RES = Use Original
    ELEMENTS -> HTTPFetcher_2
Note: Henter objekter fra NVDB-API
HTTPFetcher_2
    PROXY_AUTH_METHOD = Basic
    TARGET_ATTR = _url_contents
    TRANSFER_TIMEOUT_LENGTH = 90
    ERROR_ATTR = _error
    USE_COOKIES = No
    REQUEST_HEADER:
      GET /vegobjekter HTTP/1.1
      Accept: application/vnd.vegvesen.nvdb-v1+xml
    CONNECTION_TIMEOUT_LENGTH = 60
    SAVE_FILE = No
    STATUS_CODE_ATTR = _http_status_code
    TARGET_URL = https://www.vegvesen.no/nvdb/api/sok?kriterie={"lokasjon":{$(lokasjon)},"objektTyper":[{"id":96,"antall":$(maxFeatures),"filter":[{"type":"Skiltnummer","operator":"=","verdi":["@Value(_skiltnummer)"]}]}]}
    FOLLOW_REDIRECTS = Yes
    RESPONSE_HEADER_LIST_ATTR = _headers
    VERIFY_SSL_CERTIFICATES = Yes
    -> XMLFeatureMapper
Note: Tolker XML
XMLFeatureMapper
    FEATURE_TYPE_ATTR = fme_feature_type
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt vegreferanse{}.fylke vegreferanse{}.kommune
    XML_SOURCE_NAME = _xml_source_
    CONFIGURATION_TYPE = Single xfMap file
    XML_INPUT_TYPE = Attribute with XML document
    FEATURE_COUNT_PER_XML = _xml_feature_count_
    ATTRIBUTE_XML = _url_contents
    MERGE_ATTRS = Yes
    SINGLE_XFMAP = $(xfmap_api)
    MAPPED -> GeometryReplacer
Note: Tildeler geometri
GeometryReplacer
    REMOVE_ATTRIBUTE = Yes
    OGC_WKT_PRECISION_DISPLAY = 64-bit
    KIND_LONG = OGC Well Known Text
    SOURCE = @Value(geometriUtm33)
    -> CoordinateSystemSetter
CoordinateSystemSetter
    COORDSYS = $(coordsys)
    -> CoordinateExtractor
CoordinateExtractor
    MODE = Specify Coordinate
    Z_ATTR = _z
    Z_DEFAULT = -9999
    Y_ATTR = _y
    IND = 0
    X_ATTR = _x
    -> AttributeExposer
