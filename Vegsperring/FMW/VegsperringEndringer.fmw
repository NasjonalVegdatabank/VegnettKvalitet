FME workspace VegsperringEndringer.fmw

Parameters:
- SourceDataset_XLSXR = C:\DATA\SkiltFeltanalyse\Data\VegsperringKryss.xlsx   # Source Microsoft Excel File(s)
- SourceDataset_XLSXR_3 = C:\DATA\SkiltFeltanalyse\Data\ForrigeVegsperringKryss.xlsx   # Source Microsoft Excel File(s)

Readers:
- XLSXR_1: XLSXR from $(SourceDataset_XLSXR)
- XLSXR_2: XLSXR from $(SourceDataset_XLSXR_3)

Note: Reader Type: Microsoft Excel / Feature Type: Avviksliste / Dataset: ForrigeVegsperringKryss [XLSXR] / Geometry: xlsx_none / Parameters: / Start Row:: / End Row:: / Attributes: / NVDB_ID: number(10,0) / fylke: number(3,0) / kommune: number(3,0) / vegkategori: char(2) / vegstatus: char(2) / vegnummer: number(6,0) / hovedParsell: number(3,0) / meter: number(6,0) / lenkeId: char(8) / posisjon: number(31,15) / east: char(18) / north: number(17,8)
Avviksliste (reader XLSXR_2)
    attributes: NVDB_ID number(10,0), fylke number(3,0), kommune number(3,0), vegkategori char(2), vegstatus char(2), vegnummer number(6,0), hovedParsell number(3,0), meter number(6,0), lenkeId char(8), posisjon number(31,15), east char(18), north number(17,8)
    -> FeatureMerger [REQUESTOR]
    -> DuplicateFilter
DuplicateFilter
    KEYATTR = NVDB_ID
    INPUT_ORDERED_CHOICE = No
    UNIQUE -> DuplicateFilter_Unique
    DUPLICATE -> DuplicateFilter_Duplicate
DuplicateFilter_Unique: Inspector
DuplicateFilter_Duplicate: Inspector
Note: Reader Type: Microsoft Excel / Feature Type: Avviksliste / Dataset: VegsperringKryss [XLSXR] / Geometry: xlsx_none / Parameters: / Start Row:: / End Row:: / Attributes: / NVDB_ID: number(10,0) / fylke: number(3,0) / kommune: number(3,0) / vegkategori: char(2) / vegstatus: char(2) / vegnummer: number(6,0) / hovedParsell: number(4,0) / meter: number(6,0) / lenkeId: char(8) / posisjon: number(31,15) / east: char(18) / north: number(17,8)
Avviksliste (reader XLSXR_1)
    attributes: NVDB_ID number(10,0), fylke number(3,0), kommune number(3,0), vegkategori char(2), vegstatus char(2), vegnummer number(6,0), hovedParsell number(4,0), meter number(6,0), lenkeId char(8), posisjon number(31,15), east char(18), north number(17,8)
    -> FeatureMerger [SUPPLIER]
    -> DuplicateFilter_2
FeatureMerger
    PROCESS_DUPS = No
    MERGE_TYPE = Attributes Only
    SUPPLIERS_FIRST = No
    REJECT_NULL_MISSING_KEYS = No
    ATTR_CONFLICT_RES = Use Requestor
    IGNORE_NULLS = No
    ATTR_ACCUM_MODE = Merge Supplier
    JOIN_KEYS = @Value(NVDB_ID) @Value(NVDB_ID) AUTO
    MERGED -> FeatureMerger_Merged
    NOT_MERGED -> FeatureMerger_NotMerged
    UNREFERENCED -> FeatureMerger_Unreferenced
    DUPLICATE_SUPPLIER -> FeatureMerger_DuplicateSupplier
FeatureMerger_Merged: Inspector
FeatureMerger_NotMerged: Inspector
FeatureMerger_Unreferenced: Inspector
FeatureMerger_DuplicateSupplier: Inspector
DuplicateFilter_2
    KEYATTR = NVDB_ID
    INPUT_ORDERED_CHOICE = No
    UNIQUE -> DuplicateFilter_Unique_2
    DUPLICATE -> DuplicateFilter_Duplicate_2
DuplicateFilter_Unique_2: Inspector
DuplicateFilter_Duplicate_2: Inspector
