FME workspace VegsperringKryss.fmw

Parameters:
- START = 1   # Første fylkesnummer
- NUM = 20   # Antall fylker
- OFFSET = 1.5   # Avstand fra kryss
- dataFolder = O:\1\Res\16080 Geodata\Fagområde Vegnett\Vegnett spesialistfunksjon\Feil og kvalitetskontroller i NVDB\FME-kontroller\Vegsperring\Data   # Mappe for resultatfiler
- xfmap_api = O:\1\Res\16080 Geodata\Fagområde Vegnett\Vegnett spesialistfunksjon\Feil og kvalitetskontroller i NVDB\FME-kontroller\Felles\API_Mapping.xmp   # xfMap for API-mapping
- coordsys = EPSG:25833   # Koordinatsystem
- maxFeatures = 10000   # Maximal number of features
- DestDataset_SPATIALITE = FME_MacroValues['dataFolder'] + "\\VegsperringKryss.db"   # Python Script
- DestDataset_XLSXW2 = FME_MacroValues['dataFolder'] + "\\VegsperringKryss.xlsx"   # Python Script

Writers:
- SPATIALITE_1: SPATIALITE to $(DestDataset_SPATIALITE)
- XLSXW2_1: XLSXW2 to $(DestDataset_XLSXW2)

ListExploder_2
    ATTR_ACCUM_MODE = Merge Incoming List
    INDEX_ATTR = _element_index
    LIST_ATTR = vegreferanse{}
    ATTR_CONFLICT_RES = Use Original
    ELEMENTS -> ListExploder_3
ListExploder_3
    ATTR_ACCUM_MODE = Merge Incoming List
    INDEX_ATTR = _element_index
    LIST_ATTR = lineærPosisjon{}
    ATTR_CONFLICT_RES = Use Original
    ELEMENTS -> AttributeRenamer_2
AttributeRenamer_2
    ATTR_LIST = lineærtObjektIdentifikasjon.Identifikasjon.lokalId,lenkeId,,fraPosisjon,posisjon,,Vegreferanse.fylke,fylke,,Vegreferanse.kommune,kommune,,Vegreferanse.vegkategori,vegkategori,,Vegreferanse.vegnummer,vegnummer,,Vegreferanse.hovedParsell,hovedParsell,,Vegreferanse.veglenkeMeterFra,meter,,Vegreferanse.vegstatus,vegstatus,,_x,east,,_y,north,
    -> SpatialFilter [Candidate]
Vegsperringer: Inspector
Note: Finner Vegsperringer som ligger nær krysss
SpatialFilter
    CURVE_BOUNDARY_RULE_PARAM = Default Rule
    PREDATTR = _predicate
    ATTR_CONFLICT_RES = Use Candidate
    PREDICATES = INTERSECTS
    AGGREGATE_HANDLING = Yes
    USE_BOUNDING_BOX = No
    BASE_TYPE = Multiple Filters
    ATTR_ACCUM_MODE = Merge Filter
    PASS_CRITERIA = Pass Against One Filter
    PASSED -> AttributeRenamer_3
    PASSED -> Avviksliste (writer XLSXW2_1)
Avviksliste (writer XLSXW2_1)
    attributes: NVDB_ID auto(20), fylke auto(20), kommune auto(20), vegkategori auto(20), vegstatus auto(20), vegnummer auto(20), hovedParsell auto(20), meter auto(20), lenkeId auto(20), posisjon auto(20), east auto(20), north auto(20)
AttributeRenamer_3
    ATTR_LIST = NVDB_ID,nvdb_id,,hovedParsell,hovedparsell,,lenkeId,lenkeid,
    -> avviksliste (writer SPATIALITE_1)
avviksliste (writer SPATIALITE_1)
    attributes: nvdb_id real(31,15), fylke real(31,15), kommune real(31,15), vegkategori string(2), vegstatus string(2), vegnummer real(31,15), hovedparsell real(31,15), meter real(31,15), lenkeid string(8), posisjon string(255), east real(31,15), north real(31,15)
Transportlenke: Inspector

Bookmark: Utvalg (antall fylker og nummer)
Creator_3
    GEOMTYPE = Geometry Object
    NUM = $(NUM)
    CREATED -> Counter_2
Counter_2
    START = $(START)
    CNT_ATTR = _count
    SCOPE = Global
    DOMAIN = counter
    -> AttributeCreator

Bookmark: Leser vegsperringer fra NVDB API
AttributeCreator
    ATTR_TABLE = SET_TO _api = https://www.vegvesen.no/nvdb/api/sok?kriterie={"lokasjon":{"fylke":["@Value(_count)"]},"objektTyper":[{"id":607,"antall":"10000","filter":[]}]}
    -> HTTPFetcher_2
Note: Henter objekter fra NVDB-API
HTTPFetcher_2
    TARGET_ATTR = _url_contents
    FOLLOW_REDIRECTS = Yes
    REQUEST_HEADER:
      GET /vegobjekter HTTP/1.1
      Accept: application/vnd.vegvesen.nvdb-v1+xml
    STATUS_CODE_ATTR = _http_status_code
    CONNECTION_TIMEOUT_LENGTH = 60
    SAVE_FILE = No
    USE_COOKIES = No
    ERROR_ATTR = _error
    RESPONSE_HEADER_LIST_ATTR = _headers
    PROXY_AUTH_METHOD = Basic
    VERIFY_SSL_CERTIFICATES = Yes
    TARGET_URL = @Value(_api)
    TRANSFER_TIMEOUT_LENGTH = 90
    -> XMLFeatureMapper
Note: Tolker XML
XMLFeatureMapper
    MERGE_ATTRS = Yes
    XML_SOURCE_NAME = _xml_source_
    FEATURE_TYPE_ATTR = fme_feature_type
    ATTRIBUTE_XML = _url_contents
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt vegreferanse{}.fylke vegreferanse{}.kommune
    SINGLE_XFMAP = $(xfmap_api)
    FEATURE_COUNT_PER_XML = _xml_feature_count_
    XML_INPUT_TYPE = Attribute with XML document
    CONFIGURATION_TYPE = Single xfMap file
    MAPPED -> GeometryReplacer
Note: Tildeler geometri
GeometryReplacer
    KIND_LONG = OGC Well Known Text
    SOURCE = @Value(geometriUtm33)
    OGC_WKT_PRECISION_DISPLAY = 64-bit
    REMOVE_ATTRIBUTE = Yes
    -> CoordinateSystemSetter
CoordinateSystemSetter
    COORDSYS = $(coordsys)
    -> CoordinateExtractor
CoordinateExtractor
    IND = 0
    MODE = Specify Coordinate
    Z_ATTR = _z
    X_ATTR = _x
    Y_ATTR = _y
    Z_DEFAULT = -9999
    -> AttributeExposer_3
AttributeExposer_3
    ATTR_LIST = Vegreferanse.fylke,Vegreferanse.kommune,Vegreferanse.vegkategori,Vegreferanse.vegnummer,Vegreferanse.hovedParsell,Vegreferanse.veglenkeMeterFra,Vegreferanse.veglenkeMeterTil,Vegreferanse.vegstatus,NVDB_ID
    -> ListExploder_2
    -> AttributeRenamer
    -> Vegsperringer

Bookmark: Leser Transportlenkeobjekter rundt vegsperringene
AttributeRenamer
    ATTR_TABLE = RENAME_SET_DEFAULT NVDB_ID > VegsperringID
    -> Bufferer_2
Bufferer_2
    CAP_STYLE = Round
    OFFSET = 50
    INTERP_SEGMENTS = 8
    BUFFERED -> BoundsExtractor_3
BoundsExtractor_3
    ZMIN = _zmin
    XMAX = _xmax
    YMIN = _ymin
    ZMAX = _zmax
    YMAX = _ymax
    XMIN = _xmin
    -> AttributeCreator_5
AttributeCreator_5
    NUM_PRIOR_FEATURES = 0
    NUM_SUBSEQUENT_FEATURES = 0
    ATTR_LIST = _api,https://www.vegvesen.no/nvdb/api/sok?kriterie={"lokasjon":{bbox:"@Value(_xmin),@Value(_ymin),@Value(_xmax),@Value(_ymax)"},"objektTyper":[{"id":539,"antall":$(maxFeatures)}]}
    -> HTTPFetcher_3
Note: Henter objekter fra NVDB-API
HTTPFetcher_3
    TARGET_ATTR = _url_contents
    FOLLOW_REDIRECTS = Yes
    REQUEST_HEADER:
      GET /vegobjekter HTTP/1.1
      Accept: application/vnd.vegvesen.nvdb-v1+xml
    STATUS_CODE_ATTR = _http_status_code
    CONNECTION_TIMEOUT_LENGTH = 60
    SAVE_FILE = No
    USE_COOKIES = No
    ERROR_ATTR = _error
    RESPONSE_HEADER_LIST_ATTR = _headers
    PROXY_AUTH_METHOD = Basic
    VERIFY_SSL_CERTIFICATES = Yes
    TARGET_URL = @Value(_api)
    TRANSFER_TIMEOUT_LENGTH = 90
    -> XMLFeatureMapper_2
Note: Tolker XML
XMLFeatureMapper_2
    MERGE_ATTRS = Yes
    XML_SOURCE_NAME = _xml_source_
    FEATURE_TYPE_ATTR = fme_feature_type
    ATTRIBUTE_XML = _url_contents
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt vegreferanse{}.fylke vegreferanse{}.kommune
    SINGLE_XFMAP = $(xfmap_api)
    FEATURE_COUNT_PER_XML = _xml_feature_count_
    XML_INPUT_TYPE = Attribute with XML document
    CONFIGURATION_TYPE = Single xfMap file
    MAPPED -> GeometryReplacer_2
Note: Tildeler geometri
GeometryReplacer_2
    KIND_LONG = OGC Well Known Text
    SOURCE = @Value(geometriUtm33)
    OGC_WKT_PRECISION_DISPLAY = 64-bit
    REMOVE_ATTRIBUTE = Yes
    -> CoordinateSystemSetter_2
Note: Setter koordinatsystem
CoordinateSystemSetter_2
    COORDSYS = $(coordsys)
    -> TopologyBuilder
    -> Transportlenke

Bookmark: Danner topologi og finner kryss med minst tre lenker
TopologyBuilder
    ALLOW_CYCLES = No
    CLEAN_DATA = Yes
    OVERLAPPING_MODE = No
    DEAGGREGATE_INPUT = Yes
    MAX = 0
    GROUP_BY = VegsperringID
    PROP_ATTRS = No
    BOUNDING_EDGES = All
    NODE -> AttributeKeeper
AttributeKeeper
    KEEP_LIST = _node_angle{}.fme_arc_angle _node_angle{}.fme_arc_id
    KEEP_ATTRS = _node_number
    -> ListElementCounter
ListElementCounter
    CNT_ATTR = _element_count
    LIST_NAME = _node_angle{}
    -> TestFilter
TestFilter
    TEST_LIST = BOOL_OP,OR,COMPOSITE_TEST,<Unused>,TEST_CLAUSE,"TEST @Value(_element_count) >= 3",MinstTre
    DEFAULT_VALUE = <UNFILTERED>
    MinstTre -> Bufferer
    MinstTre -> MinstTre
Bufferer
    CAP_STYLE = Round
    OFFSET = $(OFFSET)
    INTERP_SEGMENTS = 8
    BUFFERED -> SpatialFilter [Filter]
MinstTre: Inspector
