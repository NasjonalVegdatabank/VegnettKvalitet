FME workspace xlsxr2xlsxw.fmw

Parameters:
- SourceDataset_XLSXR_3 = C:\DATA\GitHub\VegnettKvalitet\Fylkesvegnummer\Data\20170122_Fylkesvegnummer.xlsx   # Source Microsoft Excel File(s)
- DestDataset_XLSXW = C:\DATA\GitHub\VegnettKvalitet\Fylkesvegnummer\Data\Fylkesvegnummer.xlsx   # Destination Microsoft Excel File

Readers:
- XLSXR_2: XLSXR from $(SourceDataset_XLSXR_3)

Writers:
- XLSXW_1: XLSXW to $(DestDataset_XLSXW)

Ikke-unike nummer (reader XLSXR_2)
    attributes: fylkesnummer number(3,0), vegnummer number(4,0), lengde char(17), antall_parseller number(3,0), vegfunksjon char(20)
    -> FeatureMerger [REQUESTOR]
    -> AttributeManager_3_OUTPUT_-__AttributeManager_4
unike nummer (reader XLSXR_2)
    attributes: fylkesnummer number(3,0), vegnummer number(4,0), lengde char(17), antall_parseller number(3,0), vegfunksjon char(20), F string, G string, H string, I string, J string, K string, L string, M string
    -> FeatureMerger [SUPPLIER]
FeatureMerger
    SUPPLIERS_FIRST = No
    PROCESS_DUPS = Yes
    ATTR_ACCUM_MODE = Only Use Supplier
    GEOM_TYPE = Build Polygons
    REJECT_NULL_MISSING_KEYS = No
    CONNECT_Z_MODE = First Wins
    MERGE_TYPE = Attributes Only
    JOIN_KEYS = @Value(fylkesnummer) @Value(fylkesnummer) AUTO @Value(vegnummer) @Value(vegnummer) AUTO
    MERGED -> AttributeManager_3
    UNREFERENCED -> FeatureMerger_UNREFERENCED_-__AttributeManager_3_OUTPUT_-__AttributeManager_4
AttributeManager_3
    ATTR_TABLE = SET_TO fme_feature_type = Ikke-unike nummer
    -> AttributeManager_3_OUTPUT_-__AttributeManager_4
FeatureMerger_UNREFERENCED_-__AttributeManager_3_OUTPUT_-__AttributeManager_4: Junction
    -> AttributeManager_3_OUTPUT_-__AttributeManager_4
AttributeManager_3_OUTPUT_-__AttributeManager_4: Junction
    -> TestFilter_3
TestFilter_3
    DEFAULT_VALUE = <UNFILTERED>
    TEST_LIST = BOOL_OP,OR,COMPOSITE_TEST,<Unused>,TEST_CLAUSE,"TEST @Value(vegnummer) > 999",fiktive
    <UNFILTERED> -> TestFilter
    <UNFILTERED> -> TestFilter_2
TestFilter
    DEFAULT_VALUE = <UNFILTERED>
    TEST_LIST = BOOL_OP,OR,COMPOSITE_TEST,<Unused>,TEST_CLAUSE,"TEST @Value(vegfunksjon) = Primære fylkesveger",PFV
    PFV -> FeatureMerger_2 [REQUESTOR]
    PFV -> Aggregator
TestFilter_2
    DEFAULT_VALUE = <UNFILTERED>
    TEST_LIST = BOOL_OP,OR,COMPOSITE_TEST,<Unused>,TEST_CLAUSE,"TEST @Value(vegfunksjon) = Annen",Annen
    Annen -> FeatureMerger_2 [SUPPLIER]
FeatureMerger_2
    SUPPLIERS_FIRST = No
    PROCESS_DUPS = Yes
    ATTR_ACCUM_MODE = Only Use Supplier
    MERGE_COUNT_ATTR = _supplierCount
    GEOM_TYPE = Build Polygons
    REJECT_NULL_MISSING_KEYS = No
    CONNECT_Z_MODE = First Wins
    MERGE_TYPE = Attributes Only
    JOIN_KEYS = @Value(fylkesnummer) @Value(fylkesnummer) AUTO @Value(vegnummer) @Value(vegnummer) AUTO
    MERGED -> AttributeManager
    UNREFERENCED -> Aggregator
AttributeManager
    ATTR_TABLE = SET_TO vegfunksjon = Primære fylkesveger
    -> Aggregator
Aggregator
    SUM = lengde antall_parseller
    AGGREGATE_TYPE = Homogeneous Collection (If Possible)
    SEP = ,
    ORDERED = No
    MODE = Geometry - Assemble One Level
    GROUP_BY = fme_feature_type vegnummer fylkesnummer vegfunksjon fme_basename
    ACCUM_ATTRS_NAME = Get Attributes From One Representative Feature
    AGGREGATE -> Aggregator_3
    AGGREGATE -> AttributeFilter
AttributeFilter
    ATTR_NAME = fme_feature_type
    ATTR_VALUES = <EMPTY>,<MISSING>,<NULL>,<UNFILTERED>,unike nummer,Ikke-unike nummer
    unike nummer -> unike nummer (writer XLSXW_1)
    Ikke-unike nummer -> Ikke-unike nummer (writer XLSXW_1)
unike nummer (writer XLSXW_1)
    attributes: fylkesnummer number(20), vegnummer number(20), lengde number(20), antall_parseller number(20), vegfunksjon number(20)
Ikke-unike nummer (writer XLSXW_1)
    attributes: fylkesnummer number(20), vegnummer number(20), lengde number(20), antall_parseller number(20), vegfunksjon number(20)
Aggregator_3
    SUM = lengde
    AGGREGATE_TYPE = Homogeneous Collection (If Possible)
    SEP = ,
    ORDERED = No
    MODE = Geometry - Assemble One Level
    COUNT_ATTR = fylker
    GROUP_BY = vegnummer
    ACCUM_ATTRS_NAME = Get Attributes From One Representative Feature
    AGGREGATE -> AttributeManager_2
AttributeManager_2
    ATTR_TABLE:
      RENAME_SET_VALUE fylker > antall_fylker
      SET_TO antall_endres = @Evaluate(@Value(antall_fylker)-1)
    -> antall endres (writer XLSXW_1)
antall endres (writer XLSXW_1)
    attributes: vegnummer number(20), lengde number(20), antall_fylker number(20), antall_endres number(20)
