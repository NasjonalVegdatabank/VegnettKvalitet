FME workspace Fylkesvegnummer.fmw

Parameters:
- ftID = 532   # NVDB Vegobjekttype-ID
- omr = fylke   # Områdetype
- NUM = 20   # Number to Create
- START = 1   # Første nummer
- DestDataset_XLSXW = C:\DATA\GitHub\VegnettKvalitet\Fylkesvegnummer\Data\Fylkesvegnummer.xlsx   # Destination Microsoft Excel File
- DestDataset_SPATIALITE = C:\DATA\GitHub\VegnettKvalitet\Fylkesvegnummer\Data\Fylkesvegnummer.db   # Destination SpatiaLite Database File
- TNElocal = C:\DATA\TNE\data\tne_local_fylkesveg.db   # Local TNE-kopi

Readers:
- SPATIALITE_1: SPATIALITE from $(TNElocal)

Writers:
- XLSXW_1: XLSXW to $(DestDataset_XLSXW)
- SPATIALITE_2: SPATIALITE to $(DestDataset_SPATIALITE)

AttributeExposer
    ATTR_LIST = fylkesnummer,kommunenummer,vegkategori,vegnummer,hovedparsell,vegstatus
    -> TestFilter
Note: Fjerner fikitve veger og konnekteringslenker
TestFilter
    DEFAULT_VALUE = <UNFILTERED>
    TEST_LIST = BOOL_OP,OR,COMPOSITE_TEST,<Unused>,TEST_CLAUSE,"TEST @Value(vegnummer) > 9999",Fiktive,BOOL_OP,OR,COMPOSITE_TEST,<Unused>,TEST_CLAUSE,"TEST @Value(hovedparsell) IN 600-699",Konnekteringslenker
    <UNFILTERED> -> LengthCalculator
LengthCalculator
    LEN_ATTR = _length
    DIM = 2
    MULT = 1
    -> AttributeManager_3
AttributeManager_3
    ATTR_TABLE:
      REMOVE epsg
      RENAME_SET_VALUE lokasjon.stedfestinger.stedfesting.veglenkeid > route_id
      RENAME_SET_VALUE lokasjon.stedfestinger.stedfesting.fra_posisjon > from_measure
      RENAME_SET_VALUE lokasjon.stedfestinger.stedfesting.til_posisjon > to_measure
    -> InlineQuerier [Vegreferanse]
    -> FeatureMerger [REQUESTOR]
vegfunksjon (reader SPATIALITE_1)
    attributes: objectid integer, netobjecttv_id string(255), from_date integer, to_date integer, seq_no integer, ba_200705_oid string(255), vf_5178 integer, route_id string(255), from_measure real(20,10), to_measure real(20,10), topology_level integer, shape_len real(20,10)
    -> AttributeManager_2
AttributeManager_2
    ATTR_TABLE:
      REMOVE objectid
      REMOVE netobjecttv_id
      REMOVE from_date
      REMOVE to_date
      REMOVE seq_no
      REMOVE ba_200705_oid
      REMOVE vf_5178
      REMOVE topology_level
      REMOVE shape_len
      SET_TO vegfunksjon = Primære fylkesveger
    -> InlineQuerier [Vegfunksjon]
    -> VegfunksjonPFV
InlineQuerier
    TABLE_DEF = Vegreferanse,id,varchar(200),geometri.wkt,varchar(200),xml_fragment,varchar(200),xml_id,varchar(200),xml_matched_element,varchar(200),xml_parent_id,varchar(200),xml_parent_child_pos,varchar(200),fme_feature_type,varchar(200),identifikasjon.Identifikasjon.lokalId,varchar(200),identifikasjon.Identifikasjon.versjonId,varchar(200),identifikasjon.Identifikasjon.navnerom,varchar(200),gml_id,varchar(200),assosiasjoner{}.typeId,varchar(200),assosiasjoner{}.vegobjektId,varchar(200),assosiasjoner{}.relasjonstype,varchar(200),route_id,varchar(200),from_measure,varchar(200),to_measure,varchar(200),_hierarchy_child_id_list{},varchar(200),_geometry_name,varchar(200),_hierarchy_id,varchar(200),_hierarchy_parent_id,varchar(200),_part_number,varchar(200),_schemamapper_row_ids,varchar(200),fylkesnummer,varchar(200),kommunenummer,varchar(200),vegkategori,varchar(200),vegnummer,varchar(200),hovedparsell,varchar(200),vegstatus,varchar(200),_length,varchar(200),Vegfunksjon,route_id,varchar(255),from_measure,"real(20,10)",to_measure,"real(20,10)",vegfunksjon,varchar(200)
    QUERY_DEF:
      PFV,SELECT * FROM Vegreferanse
      LEFT JOIN Vegfunksjon ON Vegreferanse.route_id = Vegfunksjon.route_id
      WHERE (Vegreferanse.from_measure < Vegfunksjon.to_measure AND Vegreferanse.to_measure > Vegfunksjon.from_measure)
      ,FIRST
    QUERY_SCHEMA = PFV,id,varchar(200),geometri.wkt,varchar(200),xml_fragment,varchar(200),xml_id,varchar(200),xml_matched_element,varchar(200),xml_parent_id,varchar(200),xml_parent_child_pos,varchar(200),fme_feature_type,varchar(200),identifikasjon.Identifikasjon.lokalId,varchar(200),identifikasjon.Identifikasjon.versjonId,varchar(200),identifikasjon.Identifikasjon.navnerom,varchar(200),gml_id,varchar(200),assosiasjoner{}.typeId,varchar(200),assosiasjoner{}.vegobjektId,varchar(200),assosiasjoner{}.relasjonstype,varchar(200),route_id,varchar(200),from_measure,varchar(200),to_measure,varchar(200),_hierarchy_child_id_list{},varchar(200),_geometry_name,varchar(200),_hierarchy_id,varchar(200),_hierarchy_parent_id,varchar(200),_part_number,varchar(200),_schemamapper_row_ids,varchar(200),fylkesnummer,varchar(200),kommunenummer,varchar(200),vegkategori,varchar(200),vegnummer,varchar(200),hovedparsell,varchar(200),vegstatus,varchar(200),_length,varchar(200),Vegreferanse.fme_feature_content,fme_feature_content,vegfunksjon,varchar(200),Vegfunksjon.fme_feature_content,fme_feature_content
    PFV -> FeatureMerger [SUPPLIER]
Note: Kobler alle vegreferanseobjekter for veger med primær fylkesveg
FeatureMerger
    PROCESS_DUPS = No
    ATTR_ACCUM_MODE = Merge Supplier
    MERGE_TYPE = Attributes Only
    SUPPLIERS_FIRST = No
    ATTR_CONFLICT_RES = Use Requestor
    REJECT_NULL_MISSING_KEYS = No
    JOIN_KEYS = @Value(fylkesnummer) @Value(fylkesnummer) AUTO @Value(vegnummer) @Value(vegnummer) AUTO @Value(vegkategori) @Value(vegkategori) AUTO
    IGNORE_NULLS = No
    MERGED -> Aggregator_2
    NOT_MERGED -> AttributeManager_4
Note: Vegfunksjon "Annen"
AttributeManager_4
    ATTR_TABLE = SET_TO vegfunksjon = Annen
    -> Aggregator_2
Note: Grupper t.o.m. HP
Aggregator_2
    SEP = ,
    SUM = _length
    AGGREGATE_TYPE = Homogeneous Collection (If Possible)
    ACCUM_ATTRS_NAME = Get Attributes From One Representative Feature
    GROUP_BY = hovedparsell vegnummer fylkesnummer vegkategori
    ORDERED = No
    MODE = Geometry - Assemble One Level
    AGGREGATE -> Aggregator
Note: Grupper uten HP, tell HP-er
Aggregator
    SEP = ,
    SUM = _length
    COUNT_ATTR = _hpCount
    AGGREGATE_TYPE = Homogeneous Collection (If Possible)
    ACCUM_ATTRS_NAME = Get Attributes From One Representative Feature
    GROUP_BY = vegnummer fylkesnummer vegkategori
    ORDERED = No
    MODE = Geometry - Assemble One Level
    AGGREGATE -> Matcher
Note: Identifiser overlappende nummer
Matcher
    MATCH = NONE
    BLANK_AND_MISSING_DIFFER = No
    DIFFATTRS = fylkesnummer
    MATCHATTRS = vegnummer vegkategori
    LENIENT_MATCH = No
    CNT_ATTR = _match_id
    MATCH_STRATEGY = Match Selected Attributes
    MATCHED -> AttributeRenamer
    MATCHED -> Aggregator_3
    MATCHED -> AttributeManager_5
    NOT_MATCHED -> AttributeRenamer_2
    NOT_MATCHED -> AttributeManager_6
Aggregator_3 [off]
    SEP = ,
    SUM = _length
    COUNT_ATTR = fylker
    AGGREGATE_TYPE = Homogeneous Collection (If Possible)
    ACCUM_ATTRS_NAME = Get Attributes From One Representative Feature
    GROUP_BY = vegnummer
    ORDERED = No
    MODE = Geometry - Assemble One Level
    AGGREGATE -> AttributeManager
AttributeManager [off]
    ATTR_TABLE:
      RENAME_SET_VALUE _length > lengde
      RENAME_SET_VALUE fylker > antall_fylker
      SET_TO antall_endres = @Evaluate(@Value(antall_fylker)-1)
    -> antall endres (writer XLSXW_1)
antall endres (writer XLSXW_1) [off]
    attributes: vegnummer number(20), lengde number(20), antall_fylker number(20), antall_endres number(20)
AttributeRenamer [off]
    ATTR_TABLE:
      RENAME_SET_DEFAULT _length > lengde
      RENAME_SET_DEFAULT _hpCount > antall_parseller
    -> Ikke-unike nummer (writer XLSXW_1) [off]
    -> ikke_unike_nummer (writer SPATIALITE_2) [off]
    -> Ikke-unike_vegnummer [off]
Ikke-unike_vegnummer: Inspector [off]
ikke_unike_nummer (writer SPATIALITE_2) [off]
    attributes: fylkesnummer real(20,10), vegnummer real(20,10), lengde real(20,10), antall_parseller real(20,10), vegfunksjon string(20)
Ikke-unike nummer (writer XLSXW_1) [off]
    attributes: fylkesnummer number(20), vegnummer number(20), lengde number(20), antall_parseller number(20), vegfunksjon number(20)
AttributeManager_5
    ATTR_TABLE:
      RENAME_SET_VALUE _length > lengde
      REMOVE hovedparsell
      RENAME_SET_VALUE _hpCount > antall_parseller
      SET_TO Unik = Nei
    -> Fylkesveger
AttributeManager_6
    ATTR_TABLE:
      RENAME_SET_VALUE _length > lengde
      REMOVE hovedparsell
      RENAME_SET_VALUE _hpCount > antall_parseller
      SET_TO Unik = Ja
    -> Fylkesveger
Fylkesveger: Junction
    -> FeatureMerger_2 [REQUESTOR]
    -> Aggregator_4
Fylkesveger (writer XLSXW_1)
    attributes: fylkesnummer number(20), vegnummer number(20), lengde number(20), antall_parseller number(20), vegfunksjon string(20), Unik string(20), antall_fylker number(20), antall_endres number(20), antall_fylker_primær number(20)
AttributeRenamer_2 [off]
    ATTR_TABLE:
      RENAME_SET_DEFAULT _length > lengde
      RENAME_SET_DEFAULT _hpCount > antall_parseller
    -> unike_nummer (writer SPATIALITE_2) [off]
    -> Unike_vegnummer [off]
    -> unike nummer (writer XLSXW_1) [off]
Unike_vegnummer: Inspector [off]
unike_nummer (writer SPATIALITE_2) [off]
    attributes: fylkesnummer real(20,10), vegnummer real(20,10), lengde real(20,10), antall_parseller real(20,10), vegfunksjon string(20)
unike nummer (writer XLSXW_1) [off]
    attributes: fylkesnummer number(20), vegnummer number(20), lengde number(20), antall_parseller number(20), vegfunksjon string(20)
VegfunksjonPFV: Inspector

Bookmark: Utvalg (antall fylker og nummer)
Creator_2
    GEOMTYPE = Geometry Object
    NUM = $(NUM)
    CREATED -> Counter_2
Counter_2
    START = $(START)
    DOMAIN = counter
    SCOPE = Global
    CNT_ATTR = omrNvn
    -> AttributeCreator

Bookmark: Leser og tolker XML fra NVDB-API
Note: AttributeCreator [AttributeCreator:8] / Substitute Missing, Null and Empty by: No Substitution / Set 'href' to 'https://www.vegvesen.no/nvdb/api/v2/vegobjekter/532?$(omr)=@Value(omrNvn)&vegreferanse=F&antall=5000&inkluder=metadata,egenskaper,lokasjon,geometri' / Version: 8 / Last Parameter Edit: Build 16481
AttributeCreator
    ATTR_TABLE = SET_TO href = https://www.vegvesen.no/nvdb/api/v2/vegobjekter/532?$(omr)=@Value(omrNvn)&vegreferanse=F&antall=5000&inkluder=metadata,egenskaper,lokasjon,geometri
    -> NVDB_Leser [_Input]
Note: Vegreferanse
NVDB_Leser
    NESTE.HREF = @Value(href)
    -> SchemaMapper

Bookmark: Oversetter til GML-verdier og -navn
Note: Oversetter tillatte verdier til GML-verdier
SchemaMapper
    CSV__STRIP_QUOTES = yes
    MATCH_ATTRS = ptid enid
    CSV__FIELD_NAMES_AFTER_HEADER = no
    IDXSOURCECOL = ""
    DATASET = https://raw.githubusercontent.com/jetgeo/NVDBGML/master/XSD/NVDB_enMapping.csv
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    IDXDESTCOL = ""
    IDXSOURCEATTR = fme_feature_type
    CSV__DUPLICATE_DELIMS = no
    TABLE = CSV
    ROW_ID_ATTR = _schemamapper_row_ids
    CSV__ALLOW_SPACES_IN_COLUMN_NAMES = yes
    CSV__SKIP_LINES = 1
    CSV__GROUP_BY_DATASET = no
    MAP_ATTRS = enid ptid name
    CSV__IN_SEPARATOR = ;
    CSV__IN_FIELD_NAMES = YES
    CSV__SCHEMA_WITH_COL_NAMES = ptid,number,6,0,enid,number,6,0,name,char,29,,fullname,char,34,
    FORMAT = CSV
    CSV__SKIP_FOOTER = 0
    IDXDESTATTR = fme_feature_type
    CSV_SCAN_MAX_FEATURES = 1000
    CSV__SCHEMA = number,6,0,number,6,0,char,29,,char,34,
    MAPPED -> SchemaMapper_2
    UNMAPPED -> SchemaMapper_2
Note: Oversetter egenskapsnavn til GML-navn
SchemaMapper_2
    CSV__STRIP_QUOTES = yes
    MATCH_ATTRS = ft_attr ftid
    CSV__FIELD_NAMES_AFTER_HEADER = no
    IDXSOURCECOL = ""
    DATASET = https://raw.githubusercontent.com/jetgeo/NVDBGML/master/XSD/NVDB_ptMapping.csv
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXDESTCOL = ""
    IDXSOURCEATTR = fme_feature_type
    CSV__DUPLICATE_DELIMS = no
    TABLE = CSV
    ROW_ID_ATTR = _schemamapper_row_ids
    CSV__ALLOW_SPACES_IN_COLUMN_NAMES = yes
    CSV__SKIP_LINES = 1
    CSV__GROUP_BY_DATASET = no
    MAP_ATTRS = ptid name """"""
    CSV__IN_SEPARATOR = ;
    CSV__IN_FIELD_NAMES = YES
    CSV__SCHEMA_WITH_COL_NAMES = ft_attr,char,17,,ftid,number,3,0,ptid,number,6,0,name,char,22,
    FORMAT = CSV
    CSV__SKIP_FOOTER = 0
    IDXDESTATTR = fme_feature_type
    CSV_SCAN_MAX_FEATURES = 1000
    CSV__SCHEMA = char,17,,number,3,0,number,6,0,char,22,
    MAPPED -> NullAttributeMapper_3
    UNMAPPED -> NullAttributeMapper_3
NullAttributeMapper_3
    SOURCE_ATTR_VAL = Empty Null
    NULL_TREATMENT = Missing
    ATTRCHOICE = All Attributes
    -> SchemaMapper_3
Note: Oversetter objekttypenavn til GML-navn
SchemaMapper_3
    CSV__STRIP_QUOTES = yes
    CSV__FIELD_NAMES_AFTER_HEADER = no
    IDXSOURCECOL = ftid
    DATASET = https://raw.githubusercontent.com/jetgeo/NVDBGML/master/XSD/NVDB_ftMapping.csv
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXDESTCOL = name
    IDXSOURCEATTR = fme_feature_type
    CSV__DUPLICATE_DELIMS = no
    TABLE = CSV
    ROW_ID_ATTR = _schemamapper_row_ids
    CSV__ALLOW_SPACES_IN_COLUMN_NAMES = yes
    CSV__SKIP_LINES = 1
    CSV__GROUP_BY_DATASET = no
    CSV__IN_SEPARATOR = ;
    CSV__IN_FIELD_NAMES = YES
    CSV__SCHEMA_WITH_COL_NAMES = ftid,number,3,0,name,char,18,
    FORMAT = CSV
    CSV__SKIP_FOOTER = 0
    IDXDESTATTR = fme_feature_type
    CSV_SCAN_MAX_FEATURES = 1000
    CSV__SCHEMA = number,3,0,char,18,
    MAPPED -> AttributeExposer

Bookmark: Antall fylker pr veg
Aggregator_4
    SEP = ,
    COUNT_ATTR = fylker
    AGGREGATE_TYPE = Homogeneous Collection (If Possible)
    ACCUM_ATTRS_NAME = Get Attributes From One Representative Feature
    GROUP_BY = vegnummer
    ORDERED = No
    MODE = Geometry - Assemble One Level
    AGGREGATE -> AttributeManager_7
AttributeManager_7
    ATTR_TABLE:
      REMOVE fylkesnummer
      REMOVE vegkategori
      REMOVE id
      REMOVE geometri.wkt
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE assosiasjoner{}.typeId
      REMOVE assosiasjoner{}.vegobjektId
      REMOVE assosiasjoner{}.relasjonstype
      REMOVE _hierarchy_child_id_list{}
      REMOVE _geometry_name
      REMOVE _hierarchy_id
      REMOVE _hierarchy_parent_id
      REMOVE _part_number
      REMOVE _schemamapper_row_ids
      REMOVE kommunenummer
      REMOVE _match_id
      RENAME_SET_VALUE fylker > antall_fylker
      SET_TO antall_endres = @Evaluate(@Value(antall_fylker)-1)
      REMOVE vegstatus
      REMOVE route_id
      REMOVE from_measure
      REMOVE to_measure
      REMOVE vegfunksjon
      REMOVE lengde
      REMOVE antall_parseller
      REMOVE Unik
    -> FeatureMerger_2 [SUPPLIER]
FeatureMerger_2
    PROCESS_DUPS = No
    ATTR_ACCUM_MODE = Merge Supplier
    MERGE_TYPE = Attributes Only
    SUPPLIERS_FIRST = No
    ATTR_CONFLICT_RES = Use Requestor
    REJECT_NULL_MISSING_KEYS = No
    JOIN_KEYS = @Value(vegnummer) @Value(vegnummer) AUTO
    IGNORE_NULLS = No
    MERGED -> TestFilter_2

Bookmark: Antall fylker pr primære fylkesveg
TestFilter_2
    DEFAULT_VALUE = <UNFILTERED>
    TEST_LIST = BOOL_OP,OR,COMPOSITE_TEST,<Unused>,TEST_CLAUSE,"TEST @Value(vegfunksjon) = Primære fylkesveger",Primære fylkesveger
    Primære fylkesveger -> Aggregator_5
    Primære fylkesveger -> FeatureMerger_3 [REQUESTOR]
    <UNFILTERED> -> Fylkesveger (writer XLSXW_1)
Aggregator_5
    SEP = ,
    COUNT_ATTR = antall_fylker
    AGGREGATE_TYPE = Homogeneous Collection (If Possible)
    ACCUM_ATTRS_NAME = Get Attributes From One Representative Feature
    GROUP_BY = vegnummer
    ORDERED = No
    MODE = Geometry - Assemble One Level
    AGGREGATE -> AttributeManager_8
AttributeManager_8
    ATTR_TABLE:
      REMOVE fylkesnummer
      REMOVE lengde
      REMOVE antall_parseller
      REMOVE vegfunksjon
      REMOVE Unik
      RENAME_SET_VALUE antall_fylker > antall_fylker_primær
      REMOVE vegkategori
      REMOVE id
      REMOVE geometri.wkt
      REMOVE xml_fragment
      REMOVE xml_id
      REMOVE xml_matched_element
      REMOVE xml_parent_id
      REMOVE xml_parent_child_pos
      REMOVE fme_feature_type
      REMOVE identifikasjon.Identifikasjon.lokalId
      REMOVE identifikasjon.Identifikasjon.versjonId
      REMOVE identifikasjon.Identifikasjon.navnerom
      REMOVE gml_id
      REMOVE assosiasjoner{}.typeId
      REMOVE assosiasjoner{}.vegobjektId
      REMOVE assosiasjoner{}.relasjonstype
      REMOVE route_id
      REMOVE from_measure
      REMOVE to_measure
      REMOVE _hierarchy_child_id_list{}
      REMOVE _geometry_name
      REMOVE _hierarchy_id
      REMOVE _hierarchy_parent_id
      REMOVE _part_number
      REMOVE _schemamapper_row_ids
      REMOVE kommunenummer
      REMOVE vegstatus
      REMOVE _match_id
      REMOVE antall_endres
    -> FeatureMerger_3 [SUPPLIER]
FeatureMerger_3
    PROCESS_DUPS = No
    ATTR_ACCUM_MODE = Merge Supplier
    MERGE_TYPE = Attributes Only
    SUPPLIERS_FIRST = No
    ATTR_CONFLICT_RES = Use Requestor
    REJECT_NULL_MISSING_KEYS = No
    JOIN_KEYS = @Value(vegnummer) @Value(vegnummer) AUTO
    IGNORE_NULLS = No
    MERGED -> Fylkesveger (writer XLSXW_1)

FME custom transformer NVDB_Leser
Leser og tolker data fra NVDB-API

Parameters:
- NESTE.HREF = @Value(neste.href)   # neste.href

_Input (input)
    -> HTTPCaller_2
Loop (input)
    -> HTTPCaller_2
Note: Kan det defineres at et element SKAL blli en liste? Vil i så fall kunne forenkle koden i NVDBTranslator mye. / Se under cardinality under dokumentasjon i XML Fragmenter / https://knowledge.safe.com/idea/36634/better-and-more-consistent-support-for-listscollec.html / cardinality="*/*{?}/+{}"
HTTPCaller_2
    FOLLOW_REDIRECTS = Yes
    TRANSFER_TIMEOUT_LENGTH = 90
    CONNECTION_TIMEOUT_LENGTH = 60
    VERIFY_SSL_CERTIFICATES = Yes
    STATUS_CODE_ATTR = _http_status_code
    TARGET_ATTR_ENCODING = auto-detect
    TARGET_URL = @Value(neste.href)
    ERROR_ATTR = _error
    HTTP_METHOD = GET
    RESPONSE_HEADER_LIST_ATTR = _headers
    TARGET_ATTR = _url_contents
    CUSTOM_HEADERS = Accept;application/vnd.vegvesen.nvdb-v2+xml
    USE_COOKIES = No
    SAVE_FILE = Attribute
    -> XMLFragmenter_2
    -> XMLFragmenter
    <Rejected> -> HTTPCaller_Rejected
Note: Deler opp i en XML pr vegobjekt
XMLFragmenter
    MERGE_ATTRS = No
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = id geometri.wkt
    ATTRIBUTE_XML = _url_contents
    EMBEDDED_EXPRESSIONS = vegobjekt
    XML_SOURCE_TYPE = Attribute with XML document
    FEATURE_TYPES_FORMAT_NAME = XML
    FRAGMENTS -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg lokasjon.stedfestinger.stedfesting.veglenkeid lokasjon.stedfestinger.stedfesting.fra_posisjon lokasjon.stedfestinger.stedfesting.til_posisjon
    PYTHONSOURCE:
      import fme
      import fmeobjects

      def extractNVDB_XML(feature):

          ns='vegvesen.no.nvdb'

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      # if (n == 'Kommunenummer' and v == 0):
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute('lineærPosisjon{%d}.LineærPosisjonStrekning.nettverkselement.xlink_href' % i, 'Veglenker.gml#' + ns + '.rl.' + v)
                          v = str(feature.getAttribute('lokasjon.stedfestinger.stedfesting.fra_posisjon'))
                          if v != 'None':
                              feature.setAttribute('lineærPosisjon{%d}.LineærPosisjonStrekning.fraPosisjon' % i, v)
                          v = str(feature.getAttribute('lokasjon.stedfestinger.stedfesting.til_posisjon'))
                          if v != 'None':
                              feature.setAttribute('lineærPosisjon{%d}.LineærPosisjonStrekning.tilPosisjon' % i, v)

                          v = str(feature.getAttribute('lokasjon.stedfestinger.stedfesting.sideposisjon'))
                          if v != 'None':
                              feature.setAttribute('lineærPosisjon{%d}.LineærPosisjonStrekning.sideposisjon' % i, v)

                          v = str(feature.getAttribute('lokasjon.stedfestinger.stedfesting.retning'))
                          if v != 'None':
                              feature.setAttribute('lineærPosisjon{%d}.LineærPosisjonStrekning.retning' % i, v.lower())
                          feature.setAttribute('lineærPosisjon{%d}.LineærPosisjonStrekning.lineærReferanseMetode' % i, 'normalisert')

                      else:
                          # Punktstedfesting
                          v = str(feature.getAttribute('lokasjon.stedfestinger.stedfesting.veglenkeid'))
                          if v != 'None':
                              feature.setAttribute('lineærPosisjon{%d}.LineærPosisjonPunkt.nettverkselement.xlink_href' % i, 'Veglenker.gml#' + ns + '.rl.' + v)

                          v = str(feature.getAttribute('lokasjon.stedfestinger.stedfesting.posisjon'))
                          if v != 'None':
                              feature.setAttribute('lineærPosisjon{%d}.LineærPosisjonPunkt.posisjon' % i, v)

                          v = str(feature.getAttribute('lokasjon.stedfestinger.stedfesting.sideposisjon'))
                          if v != 'None':
                              feature.setAttribute('lineærPosisjon{%d}.LineærPosisjonPunkt.sideposisjon' % i, v)
                          feature.setAttribute('lineærPosisjon{%d}.LineærPosisjonPunkt.lineærReferanseMetode' % i, 'normalisert')

                      #feature.removeAttribute('lokasjon.stedfestinger.stedfesting.veglenkeid')
                      #feature.removeAttribute('lokasjon.stedfestinger.stedfesting.fra_posisjon')
                      #feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute('lineærPosisjon{%d}.LineærPosisjonStrekning.nettverkselement.xlink_href' % i, 'Veglenker.gml#' + ns + '.rl.' + v)

                      v = str(feature.getAttribute('lokasjon.stedfestinger.stedfesting{%d}.fra_posisjon' % i))
                      if v != 'None':
                          feature.setAttribute('lineærPosisjon{%d}.LineærPosisjonStrekning.fraPosisjon' % i, v)

                      v = str(feature.getAttribute('lokasjon.stedfestinger.stedfesting{%d}.til_posisjon' % i))
                      if v != 'None':
                          feature.setAttribute('lineærPosisjon{%d}.LineærPosisjonStrekning.tilPosisjon' % i, v)

                      v = str(feature.getAttribute('lokasjon.stedfestinger.stedfesting{%d}.sideposisjon' % i))
                      if v != 'None':
                          feature.setAttribute('lineærPosisjon{%d}.LineærPosisjonStrekning.sideposisjon' % i, v)

                      v = str(feature.getAttribute('lokasjon.stedfestinger.stedfesting{%d}.retning' % i))
                      if v != 'None':
                          feature.setAttribute('lineærPosisjon{%d}.LineærPosisjonStrekning.retning' % i, v.lower())
                      feature.setAttribute('lineærPosisjon{%d}.LineærPosisjonStrekning.lineærReferanseMetode' % i, 'normalisert')

                  else:
                      # Punktstedfesting
                      v = str(feature.getAttribute('lokasjon.stedfestinger.stedfesting{%d}.veglenkeid' % i))
                      if v != 'None':
                          feature.setAttribute('lineærPosisjon{%d}.LineærPosisjonPunkt.nettverkselement.xlink_href' % i, 'Veglenker.gml#' + ns + '.rl.' + v)

                      v = str(feature.getAttribute('lokasjon.stedfestinger.stedfesting{%d}.posisjon' % i))
                      if v != 'None':
                          feature.setAttribute('lineærPosisjon{%d}.LineærPosisjonPunkt.posisjon' % i, v)

                      v = str(feature.getAttribute('lokasjon.stedfestinger.stedfesting{%d}.sideposisjon' % i))
                      if v != 'None':
                          feature.setAttribute('lineærPosisjon{%d}.LineærPosisjonPunkt.sideposisjon' % i, v)
                      feature.setAttribute('lineærPosisjon{%d}.LineærPosisjonPunkt.lineærReferanseMetode' % i, 'normalisert')

                  #feature.removeAttribute('lokasjon.stedfestinger.stedfesting{%d}.veglenkeid' % i)
                  #feature.removeAttribute('lokasjon.stedfestinger.stedfesting{%d}.fra_posisjon' % i)
                  #feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  v = str(feature.getAttribute('lokasjon.vegreferanser.vegreferanse{%d}.kategori' % i))
                  if v != 'None':
                      feature.setAttribute('vegreferanse{%d}.Vegreferanse.vegkategori' % i, v)
                      feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> GeometryReplacer
Note: Geometri
GeometryReplacer
    OGC_WKT_PRECISION_DISPLAY = 64-bit
    REMOVE_ATTRIBUTE = Yes
    KIND_LONG = OGC Well Known Text
    SOURCE = @Value(geometri)
    -> CoordinateSystemSetter
    -> CoordinateSystemSetter_2
CoordinateSystemSetter [off]
    COORDSYS = @Value(epsg)
    -> Deaggregator
CoordinateSystemSetter_2
    COORDSYS = EPSG:6173
    -> Deaggregator
XMLFragmenter_2
    MERGE_ATTRS = No
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = returnert neste.href
    ATTRIBUTE_XML = _url_contents
    EMBEDDED_EXPRESSIONS = side/metadata
    XML_SOURCE_TYPE = Attribute with XML document
    FEATURE_TYPES_FORMAT_NAME = XML
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)
HTTPCaller_Rejected: Inspector

Bookmark: Splitter multigeometrier
Deaggregator
    SPLIT_COMPOSITES = No
    LIST_ATTR_MODE_LOOKUP = LEAN
    ID_SELECTION = ID and Parent ID
    COPY_ATTR = Every Node
    ID_ATTR = _hierarchy_id
    GEOM_NAME_FIELD = _geometry_name
    CHILD_ID_ATTR = _hierarchy_child_id_list
    PART_NUMBER_FIELD = _part_number
    MODE = Flatten One Level
    EXPLODE_INSTANCES = No
    PARENT_ID_ATTR = _hierarchy_parent_id
    DEAGGREGATED -> NullAttributeMapper
NullAttributeMapper
    ATTRLIST = _part_number
    NEW_VALUE = 0
    SOURCE_ATTR_VAL = Null Empty "Missing (Selected Attributes Only)"
    NULL_TREATMENT = New Value
    ATTRCHOICE = Selected Attributes
    -> StringConcatenator
StringConcatenator
    PARM_LINE = @Value(gml_id)_@Value(_part_number)
    VAL_ATTR = gml_id
    ACTION = Create New Attribute
    -> Output (output)
Output (output)
