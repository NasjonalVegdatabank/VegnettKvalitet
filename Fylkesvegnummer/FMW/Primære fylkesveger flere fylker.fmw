FME workspace Primære fylkesveger flere fylker.fmw

Parameters:
- SourceDataset_XLSXR = C:\DATA\GitHub\VegnettKvalitet\Fylkesvegnummer\Data\Fylkesvegnummer.xlsx   # Source Microsoft Excel File(s)
- DestDataset_XLSXW = C:\DATA\GitHub\VegnettKvalitet\Fylkesvegnummer\Data\Primære fylkesveger.xlsx   # Destination Microsoft Excel File

Readers:
- XLSXR_1: XLSXR from $(SourceDataset_XLSXR)

Writers:
- XLSXW_1: XLSXW to $(DestDataset_XLSXW)

Fylkesveger (reader XLSXR_1)
    attributes: fylkesnummer number(3,0), vegnummer number(4,0), lengde char(17), antall_parseller number(4,0), vegfunksjon char(20), Unik char(4)
    -> TestFilter
TestFilter
    TEST_LIST = BOOL_OP,OR,COMPOSITE_TEST,<Unused>,TEST_CLAUSE,"TEST @Value(vegfunksjon) = Primære fylkesveger",Primære fylkesveger
    DEFAULT_VALUE = <UNFILTERED>
    Primære fylkesveger -> Aggregator
    Primære fylkesveger -> FeatureMerger [REQUESTOR]
Aggregator
    MODE = Geometry - Assemble One Level
    ACCUM_ATTRS_NAME = Get Attributes From One Representative Feature
    AGGREGATE_TYPE = Homogeneous Collection (If Possible)
    ORDERED = No
    SEP = ,
    COUNT_ATTR = antall_fylker
    GROUP_BY = vegnummer
    AGGREGATE -> AttributeManager
AttributeManager
    ATTR_TABLE:
      REMOVE fylkesnummer
      REMOVE lengde
      REMOVE antall_parseller
      REMOVE vegfunksjon
      REMOVE Unik
    -> FeatureMerger [SUPPLIER]
FeatureMerger
    ATTR_ACCUM_MODE = Merge Supplier
    ATTR_CONFLICT_RES = Use Requestor
    MERGE_TYPE = Attributes Only
    REJECT_NULL_MISSING_KEYS = No
    IGNORE_NULLS = No
    PROCESS_DUPS = No
    JOIN_KEYS = @Value(vegnummer) @Value(vegnummer) AUTO
    SUPPLIERS_FIRST = No
    MERGED -> Fylkesveger (writer XLSXW_1)
Fylkesveger (writer XLSXW_1)
    attributes: fylkesnummer number(3), vegnummer number(4), lengde string(17), antall_parseller number(4), vegfunksjon string(20), Unik string(4), antall_fylker string(4)
